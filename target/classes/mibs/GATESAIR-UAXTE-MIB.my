--
-- GATESAIR-UAXTE-MIB.my
-- MIB generated by MG-SOFT Visual MIB Builder 2018 (64-bit) Version 12.0  Build 1200
-- Monday, November 19, 2018 at 10:56:42
--

	GATESAIR-UAXTE-MIB DEFINITIONS ::= BEGIN
 
		IMPORTS
			eventCount, eventPriority, eventTimeStamp, eventDescription			
				FROM GATESAIR-COMMONVARBINDS-MIB			
			transmissionMibs, transmitters, uax, vax			
				FROM GATESAIR-SMI			
			YesNo, EnabledDisabled, SNMPEventType			
				FROM GATESAIR-TC			
			OBJECT-GROUP, MODULE-COMPLIANCE, NOTIFICATION-GROUP			
				FROM SNMPv2-CONF			
			IpAddress, Integer32, OBJECT-TYPE, MODULE-IDENTITY, OBJECT-IDENTITY, 
			NOTIFICATION-TYPE			
				FROM SNMPv2-SMI			
			TEXTUAL-CONVENTION			
				FROM SNMPv2-TC;
	
	
		-- 1.3.6.1.4.1.43768.1.2.9
		uaxteBaseMibModule MODULE-IDENTITY 
			LAST-UPDATED "201811191056Z"		-- November 19, 2018 at 10:56 GMT
			ORGANIZATION 
				"GatesAir"
			CONTACT-INFO 
				"Corey Luckhaupt cluckhau@gatesair.com"
			DESCRIPTION 
				"UAXTE Base MIB Module"
			REVISION "201811191056Z"		-- November 19, 2018 at 10:56 GMT
			DESCRIPTION 
				"Removed elements 5K and HiZ from GPS Antenna Power"
			REVISION "201811130906Z"		-- November 13, 2018 at 09:06 GMT
			DESCRIPTION 
				"1.3.6.1.4.1.43768.3.1.1.3.2.9.1.1 uaxteRtacDisabled updated description
				1.3.6.1.4.1.43768.3.1.1.3.2.8.1.7 uaxteCfgRfldFault is now obsolete
				1.3.6.1.4.1.43768.3.1.1.3.2.9.3.4 uaxteRtacLinearModeAfterAcLoss removed item 6
				1.3.6.1.4.1.43768.3.1.1.3.2.9.4.4 uaxteRtacNonLinearModeAfterAcLoss removed item 6
				1.3.6.1.4.1.43768.3.1.1.3.2.8.2.3 uaxteCfgPwrCntrlDriveLevelAdjust corrected issue of no control
				1.3.6.1.4.1.43768.3.1.1.3.2.8.2.6 uaxteCfgPwrCntrlInputAttenuatorLevelAdjust corrected issue of no control
				1.3.6.1.4.1.43768.3.1.1.3.2.14.6 uaxteGpsGnssHDOP corrected status
				"
			REVISION "201811010852Z"		-- November 01, 2018 at 08:52 GMT
			DESCRIPTION 
				"Added GPS/GLONASS Switching OIDs"
			REVISION "201808010914Z"		-- August 01, 2018 at 09:14 GMT
			DESCRIPTION 
				"updated syntax"
			REVISION "201802280923Z"		-- February 28, 2018 at 09:23 GMT
			DESCRIPTION 
				"added UaxteInputNetworkTable"
			::= { transmissionMibs 9 }

		
	
--
-- Textual conventions
--
	
		UaxteSummaryStatus ::= TEXTUAL-CONVENTION
			STATUS current
			DESCRIPTION 
				"Description."
			SYNTAX INTEGER
				{
				ok(1),
				warning(2),
				fault(3),
				na(4)
				}

		UaxteInputSelection ::= TEXTUAL-CONVENTION
			STATUS current
			DESCRIPTION 
				"Description."
			SYNTAX INTEGER
				{
				primary(1),
				secondary(2)
				}

		UaxteInputStatus ::= TEXTUAL-CONVENTION
			STATUS current
			DESCRIPTION 
				"Description."
			SYNTAX INTEGER
				{
				ok(1),
				missing(2),
				error(3),
				none(4)
				}

		UaxteInputMode ::= TEXTUAL-CONVENTION
			STATUS current
			DESCRIPTION 
				"Description."
			SYNTAX INTEGER
				{
				automatic(1),
				manual(2),
				autoReturn(3)
				}

		UaxteFaultOk ::= TEXTUAL-CONVENTION
			STATUS current
			DESCRIPTION 
				"Description."
			SYNTAX INTEGER
				{
				fault(1),
				ok(2)
				}

		UaxteWarningOk ::= TEXTUAL-CONVENTION
			STATUS current
			DESCRIPTION 
				"Description."
			SYNTAX INTEGER
				{
				warning(1),
				ok(2)
				}

		UaxteAutoManual ::= TEXTUAL-CONVENTION
			STATUS current
			DESCRIPTION 
				"Description."
			SYNTAX INTEGER
				{
				auto(1),
				manual(2)
				}

		UaxteNetworkDuplex ::= TEXTUAL-CONVENTION
			STATUS current
			DESCRIPTION 
				"Description."
			SYNTAX INTEGER
				{
				half(1),
				full(2)
				}

		UaxteFtrReferenceStatus ::= TEXTUAL-CONVENTION
			STATUS current
			DESCRIPTION 
				"Description."
			SYNTAX INTEGER
				{
				ok(1),
				fault(2),
				warning(3)
				}

		UaxtePllStatus ::= TEXTUAL-CONVENTION
			STATUS current
			DESCRIPTION 
				"Description."
			SYNTAX INTEGER
				{
				locked(1),
				notlocked(2)
				}

		UaxteInputNetworkMode ::= TEXTUAL-CONVENTION
			STATUS current
			DESCRIPTION 
				"Description."
			SYNTAX INTEGER
				{
				multicast(1),
				unicast(2)
				}

		UaxteRtacMode ::= TEXTUAL-CONVENTION
			STATUS current
			DESCRIPTION 
				"Description."
			SYNTAX INTEGER
				{
				na(1),
				adapt(2),
				bypass(3),
				hold(4),
				stored(5)
				}

		UaxteRtacModeAfterACLoss ::= TEXTUAL-CONVENTION
			STATUS current
			DESCRIPTION 
				"Description."
			SYNTAX INTEGER
				{
				adapt(1),
				bypass(2),
				hold(3),
				stored(4),
				current(5)
				}

	
--
-- Node definitions
--
	
		-- 1.3.6.1.4.1.43768.3.1.1.3
		uaxteBaseMib OBJECT-IDENTITY
			STATUS current
			DESCRIPTION 
				"Description."
			::= { transmitters 3 }

		
		-- 1.3.6.1.4.1.43768.3.1.1.3.1
		uaxteEvents OBJECT IDENTIFIER ::= { uaxteBaseMib 1 }

		
		-- 1.3.6.1.4.1.43768.3.1.1.3.1.0
		uaxteEventsV2 OBJECT IDENTIFIER ::= { uaxteEvents 0 }

		
		-- 1.3.6.1.4.1.43768.3.1.1.3.1.0.1
		uaxteOpModeEvent NOTIFICATION-TYPE
			OBJECTS { uaxteOpMode, eventCount, eventPriority, eventTimeStamp, eventDescription
				 }
			STATUS current
			DESCRIPTION 
				"Generated when the transmitter on/off states changes"
			::= { uaxteEventsV2 1 }

		
		-- 1.3.6.1.4.1.43768.3.1.1.3.1.0.2
		uaxteActiveEvent NOTIFICATION-TYPE
			OBJECTS { uaxteActive, eventCount, eventPriority, eventTimeStamp, eventDescription
				 }
			STATUS current
			DESCRIPTION 
				"Generated when the Transmitter is the Active/Not Active Transmitter. 
				Used in dual drive configurations"
			::= { uaxteEventsV2 2 }

		
		-- 1.3.6.1.4.1.43768.3.1.1.3.1.0.3
		uaxteStatusEvent NOTIFICATION-TYPE
			OBJECTS { uaxteStatus, eventCount, eventPriority, eventTimeStamp, eventDescription
				 }
			STATUS current
			DESCRIPTION 
				"Generated when the transmitter's overall summary status changes"
			::= { uaxteEventsV2 3 }

		
		-- 1.3.6.1.4.1.43768.3.1.1.3.1.0.4
		uaxteInputStatusPrimaryEvent NOTIFICATION-TYPE
			OBJECTS { uaxteInputStatusPrimary, eventCount, eventPriority, eventTimeStamp, eventDescription
				 }
			STATUS current
			DESCRIPTION 
				"Generated when the transmitter's primary input status changes"
			::= { uaxteEventsV2 4 }

		
		-- 1.3.6.1.4.1.43768.3.1.1.3.1.0.5
		uaxteInputStatusSecondaryEvent NOTIFICATION-TYPE
			OBJECTS { uaxteInputStatusSecondary, eventCount, eventPriority, eventTimeStamp, eventDescription
				 }
			STATUS current
			DESCRIPTION 
				"Generated when the transmitter's secondary input status changes"
			::= { uaxteEventsV2 5 }

		
		-- 1.3.6.1.4.1.43768.3.1.1.3.1.0.6
		uaxteInputSwitchCountCurrentEvent NOTIFICATION-TYPE
			OBJECTS { uaxteInputSwitchCountCurrent, eventCount, eventPriority, eventTimeStamp, eventDescription
				 }
			STATUS current
			DESCRIPTION 
				"Generated when the transmitter's switches input sources"
			::= { uaxteEventsV2 6 }

		
		-- 1.3.6.1.4.1.43768.3.1.1.3.1.0.7
		uaxteOutputForwardLowWarningEvent NOTIFICATION-TYPE
			OBJECTS { uaxteOutputForwardLowWarning, eventCount, eventPriority, eventTimeStamp, eventDescription
				 }
			STATUS current
			DESCRIPTION 
				"Generated when the transmitter's output power is above/below forward low warning threshold"
			::= { uaxteEventsV2 7 }

		
		-- 1.3.6.1.4.1.43768.3.1.1.3.1.0.8
		uaxteOutputForwardLowFaultEvent NOTIFICATION-TYPE
			OBJECTS { uaxteOutputForwardLowFault, eventCount, eventPriority, eventTimeStamp, eventDescription
				 }
			STATUS current
			DESCRIPTION 
				"Generated when the transmitter's output power is above/below forward low fault threshold"
			::= { uaxteEventsV2 8 }

		
		-- 1.3.6.1.4.1.43768.3.1.1.3.1.0.9
		uaxteOutputForwardHighFaultEvent NOTIFICATION-TYPE
			OBJECTS { uaxteOutputForwardHighFault, eventCount, eventPriority, eventTimeStamp, eventDescription
				 }
			STATUS current
			DESCRIPTION 
				"Generated when the transmitter's output power is above/below forward high fault threshold"
			::= { uaxteEventsV2 9 }

		
		-- 1.3.6.1.4.1.43768.3.1.1.3.1.0.10
		uaxteOutputMuteEvent NOTIFICATION-TYPE
			OBJECTS { uaxteOutputMute, eventCount, eventPriority, eventTimeStamp, eventDescription
				 }
			STATUS current
			DESCRIPTION 
				"Generated when the transmitter's is muted/unmuted"
			::= { uaxteEventsV2 10 }

		
		-- 1.3.6.1.4.1.43768.3.1.1.3.1.0.11
		uaxteRtacLinearModeEvent NOTIFICATION-TYPE
			OBJECTS { uaxteRtacLinearMode, eventCount, eventPriority, eventTimeStamp, eventDescription
				 }
			STATUS current
			DESCRIPTION 
				"Generated when the transmitter's RTAC Linear mode is changed adapt/bypass/stored/hold"
			::= { uaxteEventsV2 11 }

		
		-- 1.3.6.1.4.1.43768.3.1.1.3.1.0.12
		uaxteRtacNonLinearModeEvent NOTIFICATION-TYPE
			OBJECTS { uaxteRtacNonLinearMode, eventCount, eventPriority, eventTimeStamp, eventDescription
				 }
			STATUS current
			DESCRIPTION 
				"Generated when the transmitter's RTAC NonLinear mode is changed adapt/bypass/stored/hold"
			::= { uaxteEventsV2 12 }

		
		-- 1.3.6.1.4.1.43768.3.1.1.3.1.0.13
		uaxteRtacDisabledEvent NOTIFICATION-TYPE
			OBJECTS { uaxteRtacDisabled, eventCount, eventPriority, eventTimeStamp, eventDescription
				 }
			STATUS current
			DESCRIPTION 
				"Generated when the transmitter's RTAC mode is changed enabled/disabled"
			::= { uaxteEventsV2 13 }

		
		-- 1.3.6.1.4.1.43768.3.1.1.3.1.0.14
		uaxtePwrSupplyControllerEvent NOTIFICATION-TYPE
			OBJECTS { uaxtePwrSupplyController, eventCount, eventPriority, eventTimeStamp, eventDescription
				 }
			STATUS current
			DESCRIPTION 
				"Generated when the transmitter's power supply controller status changes"
			::= { uaxteEventsV2 14 }

		
		-- 1.3.6.1.4.1.43768.3.1.1.3.1.0.15
		uaxtePwrSupplyPwrAmpEvent NOTIFICATION-TYPE
			OBJECTS { uaxtePwrSupplyPwrAmp, eventCount, eventPriority, eventTimeStamp, eventDescription
				 }
			STATUS current
			DESCRIPTION 
				"Generated when the transmitter's power supply power amplifier status changes"
			::= { uaxteEventsV2 15 }

		
		-- 1.3.6.1.4.1.43768.3.1.1.3.1.0.16
		uaxtePwrSupplyModulatorEvent NOTIFICATION-TYPE
			OBJECTS { uaxtePwrSupplyModulator, eventCount, eventPriority, eventTimeStamp, eventDescription
				 }
			STATUS current
			DESCRIPTION 
				"Generated when the transmitter's power supply modulator status changes"
			::= { uaxteEventsV2 16 }

		
		-- 1.3.6.1.4.1.43768.3.1.1.3.1.0.17
		uaxteRtacPerfValidEvent NOTIFICATION-TYPE
			OBJECTS { uaxteRtacPerfValid, eventCount, eventPriority, eventTimeStamp, eventDescription
				 }
			STATUS current
			DESCRIPTION 
				"Generated when the RTAC Performance Readings Valid changes"
			::= { uaxteEventsV2 17 }

		
		-- 1.3.6.1.4.1.43768.3.1.1.3.1.1
		uaxteEventsV2PwrAmps OBJECT IDENTIFIER ::= { uaxteEvents 1 }

		
		-- 1.3.6.1.4.1.43768.3.1.1.3.2
		uaxteObjects OBJECT IDENTIFIER ::= { uaxteBaseMib 2 }

		
		-- 1.3.6.1.4.1.43768.3.1.1.3.2.1
		uaxteMibRevision OBJECT-TYPE
			SYNTAX OCTET STRING (SIZE (0..32))
			MAX-ACCESS read-only
			STATUS current
			DESCRIPTION
				"The revision of this MIB supported by the agent
				queried. It matches one of the revisions listed
				in the MODULE-IDENTITY."
			::= { uaxteObjects 1 }

		
		-- 1.3.6.1.4.1.43768.3.1.1.3.2.2
		uaxteVersion OBJECT IDENTIFIER ::= { uaxteObjects 2 }

		
		-- 1.3.6.1.4.1.43768.3.1.1.3.2.2.1
		uaxteVerSoftware OBJECT IDENTIFIER ::= { uaxteVersion 1 }

		
		-- 1.3.6.1.4.1.43768.3.1.1.3.2.2.1.1
		uaxteVerSwPartNumber OBJECT-TYPE
			SYNTAX OCTET STRING (SIZE (0..20))
			MAX-ACCESS read-only
			STATUS current
			DESCRIPTION
				"GatesAir software part number of this product."
			::= { uaxteVerSoftware 1 }

		
		-- 1.3.6.1.4.1.43768.3.1.1.3.2.2.1.2
		uaxteVerSwRev OBJECT-TYPE
			SYNTAX OCTET STRING (SIZE (0..20))
			MAX-ACCESS read-only
			STATUS current
			DESCRIPTION
				"Overall revision number of the software"
			::= { uaxteVerSoftware 2 }

		
		-- 1.3.6.1.4.1.43768.3.1.1.3.2.2.1.3
		uaxteVerSwUboot OBJECT-TYPE
			SYNTAX OCTET STRING (SIZE (0..20))
			MAX-ACCESS read-only
			STATUS current
			DESCRIPTION
				"Revision number of the bootloader"
			::= { uaxteVerSoftware 3 }

		
		-- 1.3.6.1.4.1.43768.3.1.1.3.2.2.1.4
		uaxteVerSwWebboot OBJECT-TYPE
			SYNTAX OCTET STRING (SIZE (0..20))
			MAX-ACCESS read-only
			STATUS current
			DESCRIPTION
				"Revision number of the webboot application"
			::= { uaxteVerSoftware 4 }

		
		-- 1.3.6.1.4.1.43768.3.1.1.3.2.2.1.5
		uaxteVerSwXtmod OBJECT-TYPE
			SYNTAX OCTET STRING (SIZE (0..20))
			MAX-ACCESS read-only
			STATUS current
			DESCRIPTION
				"Revision number of the xtmod application"
			::= { uaxteVerSoftware 5 }

		
		-- 1.3.6.1.4.1.43768.3.1.1.3.2.2.1.6
		uaxteVerSwLinux OBJECT-TYPE
			SYNTAX OCTET STRING (SIZE (0..20))
			MAX-ACCESS read-only
			STATUS current
			DESCRIPTION
				"Revision number of the linux kernel"
			::= { uaxteVerSoftware 6 }

		
		-- 1.3.6.1.4.1.43768.3.1.1.3.2.2.1.7
		uaxteVerSwDevTree OBJECT-TYPE
			SYNTAX OCTET STRING (SIZE (0..20))
			MAX-ACCESS read-only
			STATUS current
			DESCRIPTION
				"Revision number of the device tree that maps out hardware drivers"
			::= { uaxteVerSoftware 7 }

		
		-- 1.3.6.1.4.1.43768.3.1.1.3.2.2.1.8
		uaxteVerSwFpga1 OBJECT-TYPE
			SYNTAX OCTET STRING (SIZE (0..20))
			MAX-ACCESS read-only
			STATUS current
			DESCRIPTION
				"Revision number of fpga1"
			::= { uaxteVerSoftware 8 }

		
		-- 1.3.6.1.4.1.43768.3.1.1.3.2.2.1.9
		uaxteVerSwFpga2 OBJECT-TYPE
			SYNTAX OCTET STRING (SIZE (0..20))
			MAX-ACCESS read-only
			STATUS current
			DESCRIPTION
				"Revision number of fpga2, note not always used"
			::= { uaxteVerSoftware 9 }

		
		-- 1.3.6.1.4.1.43768.3.1.1.3.2.2.1.10
		uaxteVerSwCpld OBJECT-TYPE
			SYNTAX OCTET STRING (SIZE (0..20))
			MAX-ACCESS read-only
			STATUS current
			DESCRIPTION
				"Revision number of the cpld"
			::= { uaxteVerSoftware 10 }

		
		-- 1.3.6.1.4.1.43768.3.1.1.3.2.2.2
		uaxteVerHardware OBJECT IDENTIFIER ::= { uaxteVersion 2 }

		
		-- 1.3.6.1.4.1.43768.3.1.1.3.2.2.2.1
		uaxteVerHwModulator OBJECT-TYPE
			SYNTAX OCTET STRING (SIZE (0..10))
			MAX-ACCESS read-only
			STATUS current
			DESCRIPTION
				"Hardware version,config,variant,type of the modulator"
			::= { uaxteVerHardware 1 }

		
		-- 1.3.6.1.4.1.43768.3.1.1.3.2.2.2.2
		uaxteVerHwBackplane OBJECT-TYPE
			SYNTAX OCTET STRING (SIZE (0..10))
			MAX-ACCESS read-only
			STATUS current
			DESCRIPTION
				"Hardware version of the backplane"
			::= { uaxteVerHardware 2 }

		
		-- 1.3.6.1.4.1.43768.3.1.1.3.2.2.2.3
		uaxteVerHwPwrSupplyCtrl OBJECT-TYPE
			SYNTAX OCTET STRING (SIZE (0..10))
			MAX-ACCESS read-only
			STATUS current
			DESCRIPTION
				"Hardware version,config,variant,type of the power supply controller"
			::= { uaxteVerHardware 3 }

		
		-- 1.3.6.1.4.1.43768.3.1.1.3.2.2.2.4
		uaxteVerHwPwrAmp OBJECT-TYPE
			SYNTAX OCTET STRING (SIZE (0..10))
			MAX-ACCESS read-only
			STATUS current
			DESCRIPTION
				"Hardware version,config,variant,type of the power amplifier"
			::= { uaxteVerHardware 4 }

		
		-- 1.3.6.1.4.1.43768.3.1.1.3.2.3
		uaxteGeneral OBJECT IDENTIFIER ::= { uaxteObjects 3 }

		
		-- 1.3.6.1.4.1.43768.3.1.1.3.2.3.1
		uaxteOpMode OBJECT-TYPE
			SYNTAX INTEGER
				{
				on(1),
				off(2)
				}
			MAX-ACCESS read-write
			STATUS current
			DESCRIPTION
				"Operation mode of the Tranmitter, On/Off"
			::= { uaxteGeneral 1 }

		
		-- 1.3.6.1.4.1.43768.3.1.1.3.2.3.2
		uaxteActive OBJECT-TYPE
			SYNTAX INTEGER
				{
				main(1),
				standby(2)
				}
			MAX-ACCESS read-only
			STATUS current
			DESCRIPTION
				"Status of the transmitter, Main/On Air or Standby/Off Air, used in dual drive configurations."
			::= { uaxteGeneral 2 }

		
		-- 1.3.6.1.4.1.43768.3.1.1.3.2.3.3
		uaxteStatus OBJECT-TYPE
			SYNTAX UaxteSummaryStatus
			MAX-ACCESS read-only
			STATUS current
			DESCRIPTION
				"Overall status of the transmitter"
			::= { uaxteGeneral 3 }

		
		-- 1.3.6.1.4.1.43768.3.1.1.3.2.3.4
		uaxteStationName OBJECT-TYPE
			SYNTAX OCTET STRING (SIZE (0..12))
			MAX-ACCESS read-write
			STATUS current
			DESCRIPTION
				"User defined name for the exciter. This field
				is limited to 12 characters."
			::= { uaxteGeneral 4 }

		
		-- 1.3.6.1.4.1.43768.3.1.1.3.2.3.5
		uaxteModelNumber OBJECT-TYPE
			SYNTAX OCTET STRING (SIZE (0..14))
			MAX-ACCESS read-only
			STATUS current
			DESCRIPTION
				"User defined Model Number for the exciter. This field
				is limited to 14 characters."
			::= { uaxteGeneral 5 }

		
		-- 1.3.6.1.4.1.43768.3.1.1.3.2.3.6
		uaxteSerialNumber OBJECT-TYPE
			SYNTAX OCTET STRING (SIZE (0..32))
			MAX-ACCESS read-only
			STATUS current
			DESCRIPTION
				"Serial number of the exciter assembly"
			::= { uaxteGeneral 6 }

		
		-- 1.3.6.1.4.1.43768.3.1.1.3.2.4
		uaxteDateAndTime OBJECT IDENTIFIER ::= { uaxteObjects 4 }

		
		-- 1.3.6.1.4.1.43768.3.1.1.3.2.4.1
		uaxteTimeOfDay OBJECT-TYPE
			SYNTAX OCTET STRING (SIZE (0..32))
			MAX-ACCESS read-write
			STATUS current
			DESCRIPTION
				"The exciter's time of day. If NTP
				is enabled, a write to this element is acknowledged
				but ignored. The time of day is formatted in UTC time,
				e.g. YYYY-MM-DDThh:mm:ss.sTZD.
				sTZD = .04:59 - 4hrs 59min
				"
			::= { uaxteDateAndTime 1 }

		
		-- 1.3.6.1.4.1.43768.3.1.1.3.2.4.2
		uaxteUTCOffset OBJECT-TYPE
			SYNTAX Integer32
			MAX-ACCESS read-write
			STATUS current
			DESCRIPTION
				"The UTC offset for the exciter, plus or minus, in seconds."
			::= { uaxteDateAndTime 2 }

		
		-- 1.3.6.1.4.1.43768.3.1.1.3.2.4.3
		uaxteTimeSource OBJECT-TYPE
			SYNTAX INTEGER
				{
				ntp(1),
				disabled(2),
				gps(3)
				}
			MAX-ACCESS read-write
			STATUS current
			DESCRIPTION
				"The exciter time source."
			::= { uaxteDateAndTime 3 }

		
		-- 1.3.6.1.4.1.43768.3.1.1.3.2.4.4
		uaxteNTPServerName1 OBJECT-TYPE
			SYNTAX OCTET STRING (SIZE (0..32))
			MAX-ACCESS read-write
			STATUS current
			DESCRIPTION
				"IP Address or URL for the exciter's first
				NTP server source. The agent will attempt to decode a value
				written to this element as a valid unicast IP address first.
				If it fails, it will accept the string as an URL without validation."
			::= { uaxteDateAndTime 4 }

		
		-- 1.3.6.1.4.1.43768.3.1.1.3.2.4.5
		uaxteNTPServerName2 OBJECT-TYPE
			SYNTAX OCTET STRING (SIZE (0..32))
			MAX-ACCESS read-write
			STATUS current
			DESCRIPTION
				"IP Address or URL for the exciter's second
				NTP server source. The agent will attempt to decode a value
				written to this element as a valid unicast IP address first.
				If it fails, it will accept the string as an URL without validation."
			::= { uaxteDateAndTime 5 }

		
		-- 1.3.6.1.4.1.43768.3.1.1.3.2.4.6
		uaxteNTPServerName3 OBJECT-TYPE
			SYNTAX OCTET STRING (SIZE (0..32))
			MAX-ACCESS read-write
			STATUS current
			DESCRIPTION
				"IP Address or URL for the exciter's third
				NTP server source. The agent will attempt to decode a value
				written to this element as a valid unicast IP address first.
				If it fails, it will accept the string as an URL without validation."
			::= { uaxteDateAndTime 6 }

		
		-- 1.3.6.1.4.1.43768.3.1.1.3.2.4.7
		uaxteNTPServerName4 OBJECT-TYPE
			SYNTAX OCTET STRING (SIZE (0..32))
			MAX-ACCESS read-write
			STATUS current
			DESCRIPTION
				"IP Address or URL for the exciter's fourth
				NTP server source. The agent will attempt to decode a value
				written to this element as a valid unicast IP address first.
				If it fails, it will accept the string as an URL without validation."
			::= { uaxteDateAndTime 7 }

		
		-- 1.3.6.1.4.1.43768.3.1.1.3.2.4.8
		uaxteNTPServerName5 OBJECT-TYPE
			SYNTAX OCTET STRING (SIZE (0..32))
			MAX-ACCESS read-write
			STATUS current
			DESCRIPTION
				"IP Address or URL for the exciter's fifth
				NTP server source. The agent will attempt to decode a value
				written to this element as a valid unicast IP address first.
				If it fails, it will accept the string as an URL without validation."
			::= { uaxteDateAndTime 8 }

		
		-- 1.3.6.1.4.1.43768.3.1.1.3.2.5
		uaxteInput OBJECT IDENTIFIER ::= { uaxteObjects 5 }

		
		-- 1.3.6.1.4.1.43768.3.1.1.3.2.5.1
		uaxteInputPowerOn OBJECT-TYPE
			SYNTAX INTEGER
				{
				current(1),
				primary(2),
				secondary(3)
				}
			MAX-ACCESS read-write
			STATUS current
			DESCRIPTION
				"Upon bootup the selected input will be applied to the modulator.
				current = what the modulator was set to prior to AC power loss"
			::= { uaxteInput 1 }

		
		-- 1.3.6.1.4.1.43768.3.1.1.3.2.5.2
		uaxteInputActive OBJECT-TYPE
			SYNTAX UaxteInputSelection
			MAX-ACCESS read-write
			STATUS current
			DESCRIPTION
				"Active input of the transmitter"
			::= { uaxteInput 2 }

		
		-- 1.3.6.1.4.1.43768.3.1.1.3.2.5.3
		uaxteInputStatusPrimary OBJECT-TYPE
			SYNTAX UaxteInputStatus
			MAX-ACCESS read-only
			STATUS current
			DESCRIPTION
				"Status of the primary input of the transmitter"
			::= { uaxteInput 3 }

		
		-- 1.3.6.1.4.1.43768.3.1.1.3.2.5.4
		uaxteInputStatusSecondary OBJECT-TYPE
			SYNTAX UaxteInputStatus
			MAX-ACCESS read-only
			STATUS current
			DESCRIPTION
				"Status of the secondary input of the transmitter."
			::= { uaxteInput 4 }

		
		-- 1.3.6.1.4.1.43768.3.1.1.3.2.5.5
		uaxteInputMuteOnTsLoss OBJECT-TYPE
			SYNTAX YesNo
			MAX-ACCESS read-write
			STATUS current
			DESCRIPTION
				"Mute RF when TS stream is lost"
			::= { uaxteInput 5 }

		
		-- 1.3.6.1.4.1.43768.3.1.1.3.2.5.6
		uaxteInputSwitchMode OBJECT-TYPE
			SYNTAX UaxteInputMode
			MAX-ACCESS read-write
			STATUS current
			DESCRIPTION
				"Input selection mode."
			::= { uaxteInput 6 }

		
		-- 1.3.6.1.4.1.43768.3.1.1.3.2.5.7
		uaxteInputSwitchTimeout OBJECT-TYPE
			SYNTAX Integer32
			UNITS "S"
			MAX-ACCESS read-write
			STATUS current
			DESCRIPTION
				"The amount of time there can be a failure on a input
				before the transmitter switches to the other input when uaxteInputSwitchMode = 'auto'."
			::= { uaxteInput 7 }

		
		-- 1.3.6.1.4.1.43768.3.1.1.3.2.5.8
		uaxteInputSwitchElapsedTime OBJECT-TYPE
			SYNTAX Integer32
			UNITS "S"
			MAX-ACCESS read-only
			STATUS current
			DESCRIPTION
				"the amount of time currently waiting before the transmitter
				switches to the available be input"
			::= { uaxteInput 8 }

		
		-- 1.3.6.1.4.1.43768.3.1.1.3.2.5.9
		uaxteInputSwitchCountMax OBJECT-TYPE
			SYNTAX Integer32
			MAX-ACCESS read-write
			STATUS current
			DESCRIPTION
				"The maximum allowable number of automatic switchovers."
			::= { uaxteInput 9 }

		
		-- 1.3.6.1.4.1.43768.3.1.1.3.2.5.10
		uaxteInputSwitchCountCurrent OBJECT-TYPE
			SYNTAX Integer32
			MAX-ACCESS read-only
			STATUS current
			DESCRIPTION
				"The current number of times the switchover has occured."
			::= { uaxteInput 10 }

		
		-- 1.3.6.1.4.1.43768.3.1.1.3.2.5.11
		uaxteInputSwitchCountReset OBJECT-TYPE
			SYNTAX Integer32
			MAX-ACCESS read-write
			STATUS current
			DESCRIPTION
				"Command to reset the current count so automatic switchovers can occur again.
				there is no status of this OID.
				1 = execute reset of count."
			::= { uaxteInput 11 }

		
		-- 1.3.6.1.4.1.43768.3.1.1.3.2.6
		uaxtePwrAmps OBJECT IDENTIFIER ::= { uaxteObjects 6 }

		
		-- 1.3.6.1.4.1.43768.3.1.1.3.2.6.1
		uaxtePaSystem OBJECT IDENTIFIER ::= { uaxtePwrAmps 1 }

		
		-- 1.3.6.1.4.1.43768.3.1.1.3.2.6.1.1
		uaxtePaSystemFaults OBJECT IDENTIFIER ::= { uaxtePaSystem 1 }

		
		-- 1.3.6.1.4.1.43768.3.1.1.3.2.6.1.1.1
		uaxtePaSystemFaultAcMains OBJECT-TYPE
			SYNTAX UaxteFaultOk
			MAX-ACCESS read-only
			STATUS current
			DESCRIPTION
				"AC Main Fault of the entire power amplifier System"
			::= { uaxtePaSystemFaults 1 }

		
		-- 1.3.6.1.4.1.43768.3.1.1.3.2.6.1.1.2
		uaxtePaSystemFaultRs485Communication OBJECT-TYPE
			SYNTAX UaxteFaultOk
			MAX-ACCESS read-only
			STATUS current
			DESCRIPTION
				"RS485 communication fault to the entire power amplifier system"
			::= { uaxtePaSystemFaults 2 }

		
		-- 1.3.6.1.4.1.43768.3.1.1.3.2.6.1.1.3
		uaxtePaSystemSummary OBJECT-TYPE
			SYNTAX UaxteFaultOk
			MAX-ACCESS read-only
			STATUS current
			DESCRIPTION
				"Power amplifier system summary fault"
			::= { uaxtePaSystemFaults 3 }

		
		-- 1.3.6.1.4.1.43768.3.1.1.3.2.6.1.2
		uaxtePaSystemConfig OBJECT IDENTIFIER ::= { uaxtePaSystem 2 }

		
		-- 1.3.6.1.4.1.43768.3.1.1.3.2.6.1.2.1
		uaxtePaSystemNumberOfCabinets OBJECT-TYPE
			SYNTAX Integer32 (1..8)
			MAX-ACCESS read-only
			STATUS current
			DESCRIPTION
				"Number of Cabinets in this system"
			::= { uaxtePaSystemConfig 1 }

		
		-- 1.3.6.1.4.1.43768.3.1.1.3.2.6.1.2.2
		uaxtePaSystemNumberOfIPAsPerCabinet OBJECT-TYPE
			SYNTAX Integer32 (0..2)
			MAX-ACCESS read-only
			STATUS current
			DESCRIPTION
				"Number of IPAs in each cabinet"
			::= { uaxtePaSystemConfig 2 }

		
		-- 1.3.6.1.4.1.43768.3.1.1.3.2.6.1.2.3
		uaxtePaSystemNumberOfPAsPerCabinet OBJECT-TYPE
			SYNTAX Integer32 (0..12)
			MAX-ACCESS read-only
			STATUS current
			DESCRIPTION
				"Number of Power amplifiers in each cabinet"
			::= { uaxtePaSystemConfig 3 }

		
		-- 1.3.6.1.4.1.43768.3.1.1.3.2.6.1.2.4
		uaxtePaSystemNumberOfPalletsPerPAs OBJECT-TYPE
			SYNTAX Integer32 (1..8)
			MAX-ACCESS read-only
			STATUS current
			DESCRIPTION
				"Description."
			::= { uaxtePaSystemConfig 4 }

		
		-- 1.3.6.1.4.1.43768.3.1.1.3.2.6.2
		uaxtePaCab OBJECT IDENTIFIER ::= { uaxtePwrAmps 2 }

		
		-- 1.3.6.1.4.1.43768.3.1.1.3.2.6.2.1
		uaxtePaCabTable OBJECT-TYPE
			SYNTAX SEQUENCE OF UaxtePaCabEntry
			MAX-ACCESS not-accessible
			STATUS current
			DESCRIPTION
				"Description."
			::= { uaxtePaCab 1 }

		
		-- 1.3.6.1.4.1.43768.3.1.1.3.2.6.2.1.1
		uaxtePaCabEntry OBJECT-TYPE
			SYNTAX UaxtePaCabEntry
			MAX-ACCESS not-accessible
			STATUS current
			DESCRIPTION
				"Description."
			INDEX { uaxteCabIndex }
			::= { uaxtePaCabTable 1 }

		
		UaxtePaCabEntry ::=
			SEQUENCE { 
				uaxteCabIndex
					Integer32,
				uaxteCabFaultAcMain
					UaxteFaultOk,
				uaxteCabFaultPaRs485Communication
					UaxteFaultOk,
				uaxteCabFaultRs485Communication
					UaxteFaultOk,
				uaxteCabFaultSummary
					UaxteFaultOk
			 }

		-- 1.3.6.1.4.1.43768.3.1.1.3.2.6.2.1.1.1
		uaxteCabIndex OBJECT-TYPE
			SYNTAX Integer32 (1..8)
			MAX-ACCESS read-only
			STATUS current
			DESCRIPTION
				"Cabinet index in the system MAX is 8 but changes based system configuration"
			::= { uaxtePaCabEntry 1 }

		
		-- 1.3.6.1.4.1.43768.3.1.1.3.2.6.2.1.1.2
		uaxteCabFaultAcMain OBJECT-TYPE
			SYNTAX UaxteFaultOk
			MAX-ACCESS read-only
			STATUS current
			DESCRIPTION
				"1=the AC Mains is lost to entire cabinet"
			::= { uaxtePaCabEntry 2 }

		
		-- 1.3.6.1.4.1.43768.3.1.1.3.2.6.2.1.1.3
		uaxteCabFaultPaRs485Communication OBJECT-TYPE
			SYNTAX UaxteFaultOk
			MAX-ACCESS read-only
			STATUS current
			DESCRIPTION
				"1= no communications to the PAs in this cabinet"
			::= { uaxtePaCabEntry 3 }

		
		-- 1.3.6.1.4.1.43768.3.1.1.3.2.6.2.1.1.4
		uaxteCabFaultRs485Communication OBJECT-TYPE
			SYNTAX UaxteFaultOk
			MAX-ACCESS read-only
			STATUS current
			DESCRIPTION
				"1= no communications to all PAs and/or IPA in this cabinet"
			::= { uaxtePaCabEntry 4 }

		
		-- 1.3.6.1.4.1.43768.3.1.1.3.2.6.2.1.1.5
		uaxteCabFaultSummary OBJECT-TYPE
			SYNTAX UaxteFaultOk
			MAX-ACCESS read-only
			STATUS current
			DESCRIPTION
				"0 = No communication to PAs to get data.
				1 = PA is reporting a fault thru the RS485 communication.
				2 = All PA report fine. 
				."
			::= { uaxtePaCabEntry 5 }

		
		-- 1.3.6.1.4.1.43768.3.1.1.3.2.6.3
		uaxtePa OBJECT IDENTIFIER ::= { uaxtePwrAmps 3 }

		
		-- 1.3.6.1.4.1.43768.3.1.1.3.2.6.3.1
		uaxtePaTable OBJECT-TYPE
			SYNTAX SEQUENCE OF UaxtePaEntry
			MAX-ACCESS not-accessible
			STATUS current
			DESCRIPTION
				"Description."
			::= { uaxtePa 1 }

		
		-- 1.3.6.1.4.1.43768.3.1.1.3.2.6.3.1.1
		uaxtePaEntry OBJECT-TYPE
			SYNTAX UaxtePaEntry
			MAX-ACCESS not-accessible
			STATUS current
			DESCRIPTION
				"NOTE:
				Number of Cabinets in the system, MAX is 8 but changes based system configuration
				Number of PAs per Cabinet MAX is 12 but changes based system configuration"
			INDEX { uaxtePaCabIndex, uaxtePaIndex }
			::= { uaxtePaTable 1 }

		
		UaxtePaEntry ::=
			SEQUENCE { 
				uaxtePaCabIndex
					Integer32,
				uaxtePaIndex
					Integer32,
				uaxtePaOpMode
					Integer32,
				uaxtePaFwdPwr
					Integer32,
				uaxtePaRfldPwr
					Integer32,
				uaxtePaVolts
					Integer32,
				uaxtePaTemperature
					Integer32,
				uaxtePaPreAmpCurent
					Integer32,
				uaxtePaPallet1Current
					Integer32,
				uaxtePaPallet2Current
					Integer32,
				uaxtePaPallet3Current
					Integer32,
				uaxtePaPallet4Current
					Integer32,
				uaxtePaPallet5Current
					Integer32,
				uaxtePaPallet6Current
					Integer32,
				uaxtePaPallet7Current
					Integer32,
				uaxtePaPallet8Current
					Integer32,
				uaxtePaFaultAcMain
					UaxteFaultOk,
				uaxtePaFaultsRs485Communication
					INTEGER
			 }

		-- 1.3.6.1.4.1.43768.3.1.1.3.2.6.3.1.1.1
		uaxtePaCabIndex OBJECT-TYPE
			SYNTAX Integer32 (1..8)
			MAX-ACCESS read-only
			STATUS current
			DESCRIPTION
				"Cabinet index in the system MAX is 8 but changes based system configuration"
			::= { uaxtePaEntry 1 }

		
		-- 1.3.6.1.4.1.43768.3.1.1.3.2.6.3.1.1.2
		uaxtePaIndex OBJECT-TYPE
			SYNTAX Integer32 (1..12)
			MAX-ACCESS read-only
			STATUS current
			DESCRIPTION
				"Power Amplifier index in the cabinet MAX is 12 but changes based system configuration"
			::= { uaxtePaEntry 2 }

		
		-- 1.3.6.1.4.1.43768.3.1.1.3.2.6.3.1.1.3
		uaxtePaOpMode OBJECT-TYPE
			SYNTAX Integer32
			MAX-ACCESS read-only
			STATUS current
			DESCRIPTION
				"On/Off status of the Pa Module"
			::= { uaxtePaEntry 3 }

		
		-- 1.3.6.1.4.1.43768.3.1.1.3.2.6.3.1.1.4
		uaxtePaFwdPwr OBJECT-TYPE
			SYNTAX Integer32
			UNITS "watts(*0.1)"
			MAX-ACCESS read-only
			STATUS current
			DESCRIPTION
				"take reading and multiple by 0.1 for watts"
			::= { uaxtePaEntry 4 }

		
		-- 1.3.6.1.4.1.43768.3.1.1.3.2.6.3.1.1.5
		uaxtePaRfldPwr OBJECT-TYPE
			SYNTAX Integer32
			MAX-ACCESS read-only
			STATUS current
			DESCRIPTION
				"take reading and multiple by 0.1 for watts"
			::= { uaxtePaEntry 5 }

		
		-- 1.3.6.1.4.1.43768.3.1.1.3.2.6.3.1.1.6
		uaxtePaVolts OBJECT-TYPE
			SYNTAX Integer32
			MAX-ACCESS read-only
			STATUS current
			DESCRIPTION
				"take reading and multiple by 0.01 for volts"
			::= { uaxtePaEntry 6 }

		
		-- 1.3.6.1.4.1.43768.3.1.1.3.2.6.3.1.1.7
		uaxtePaTemperature OBJECT-TYPE
			SYNTAX Integer32
			MAX-ACCESS read-only
			STATUS current
			DESCRIPTION
				"take reading and multiple by 0.1 for degree C"
			::= { uaxtePaEntry 7 }

		
		-- 1.3.6.1.4.1.43768.3.1.1.3.2.6.3.1.1.8
		uaxtePaPreAmpCurent OBJECT-TYPE
			SYNTAX Integer32
			UNITS "mA"
			MAX-ACCESS read-only
			STATUS current
			DESCRIPTION
				"not used on some power amplifiers."
			::= { uaxtePaEntry 8 }

		
		-- 1.3.6.1.4.1.43768.3.1.1.3.2.6.3.1.1.9
		uaxtePaPallet1Current OBJECT-TYPE
			SYNTAX Integer32
			UNITS "mA"
			MAX-ACCESS read-only
			STATUS current
			DESCRIPTION
				"not used on 2 pallet power amplifiers.
				"
			::= { uaxtePaEntry 9 }

		
		-- 1.3.6.1.4.1.43768.3.1.1.3.2.6.3.1.1.10
		uaxtePaPallet2Current OBJECT-TYPE
			SYNTAX Integer32
			UNITS "mA"
			MAX-ACCESS read-write
			STATUS current
			DESCRIPTION
				"not used on 1 pallet power amplifiers
				"
			::= { uaxtePaEntry 10 }

		
		-- 1.3.6.1.4.1.43768.3.1.1.3.2.6.3.1.1.11
		uaxtePaPallet3Current OBJECT-TYPE
			SYNTAX Integer32
			UNITS "mA"
			MAX-ACCESS read-only
			STATUS current
			DESCRIPTION
				"Description"
			::= { uaxtePaEntry 11 }

		
		-- 1.3.6.1.4.1.43768.3.1.1.3.2.6.3.1.1.12
		uaxtePaPallet4Current OBJECT-TYPE
			SYNTAX Integer32
			UNITS "mA"
			MAX-ACCESS read-only
			STATUS current
			DESCRIPTION
				"only used on 4 or more pallet power amplifiers
				"
			::= { uaxtePaEntry 12 }

		
		-- 1.3.6.1.4.1.43768.3.1.1.3.2.6.3.1.1.13
		uaxtePaPallet5Current OBJECT-TYPE
			SYNTAX Integer32
			UNITS "mA"
			MAX-ACCESS read-only
			STATUS current
			DESCRIPTION
				"only used on 5 or more pallet power amplifiers
				"
			::= { uaxtePaEntry 13 }

		
		-- 1.3.6.1.4.1.43768.3.1.1.3.2.6.3.1.1.14
		uaxtePaPallet6Current OBJECT-TYPE
			SYNTAX Integer32
			UNITS "mA"
			MAX-ACCESS read-only
			STATUS current
			DESCRIPTION
				"only used on 6 or more pallet power amplifiers
				"
			::= { uaxtePaEntry 14 }

		
		-- 1.3.6.1.4.1.43768.3.1.1.3.2.6.3.1.1.15
		uaxtePaPallet7Current OBJECT-TYPE
			SYNTAX Integer32
			UNITS "mA"
			MAX-ACCESS read-only
			STATUS current
			DESCRIPTION
				"only used on 7 or more pallet power amplifiers
				"
			::= { uaxtePaEntry 15 }

		
		-- 1.3.6.1.4.1.43768.3.1.1.3.2.6.3.1.1.16
		uaxtePaPallet8Current OBJECT-TYPE
			SYNTAX Integer32
			UNITS "mA"
			MAX-ACCESS read-only
			STATUS current
			DESCRIPTION
				"only used on 8 pallet power amplifiers
				"
			::= { uaxtePaEntry 16 }

		
		-- 1.3.6.1.4.1.43768.3.1.1.3.2.6.3.1.1.17
		uaxtePaFaultAcMain OBJECT-TYPE
			SYNTAX UaxteFaultOk
			MAX-ACCESS read-only
			STATUS current
			DESCRIPTION
				"AC Main fault of the Pa Module"
			::= { uaxtePaEntry 17 }

		
		-- 1.3.6.1.4.1.43768.3.1.1.3.2.6.3.1.1.18
		uaxtePaFaultsRs485Communication OBJECT-TYPE
			SYNTAX INTEGER
				{
				ok(1),
				fail(2)
				}
			MAX-ACCESS read-only
			STATUS current
			DESCRIPTION
				"RS485 communication to the Pa Module"
			::= { uaxtePaEntry 18 }

		
		-- 1.3.6.1.4.1.43768.3.1.1.3.2.6.4
		uaxteIpa OBJECT IDENTIFIER ::= { uaxtePwrAmps 4 }

		
		-- 1.3.6.1.4.1.43768.3.1.1.3.2.6.4.1
		uaxteIpaTable OBJECT-TYPE
			SYNTAX SEQUENCE OF UaxteIpaEntry
			MAX-ACCESS not-accessible
			STATUS current
			DESCRIPTION
				"Description."
			::= { uaxteIpa 1 }

		
		-- 1.3.6.1.4.1.43768.3.1.1.3.2.6.4.1.1
		uaxteIpaEntry OBJECT-TYPE
			SYNTAX UaxteIpaEntry
			MAX-ACCESS not-accessible
			STATUS current
			DESCRIPTION
				"Number of Cabinets in the system, MAX is 8 but changes based system configuration
				Number of IPAs per Cabinet MAX is 2 but changes based system configuration"
			INDEX { uaxteIpaCabIndex, uaxteIpaIndex }
			::= { uaxteIpaTable 1 }

		
		UaxteIpaEntry ::=
			SEQUENCE { 
				uaxteIpaCabIndex
					Integer32,
				uaxteIpaIndex
					Integer32,
				uaxteIpaOpMode
					INTEGER,
				uaxteIpaFwdPwr
					Integer32,
				uaxteIpaRfldPwr
					Integer32,
				uaxteIpaVolts
					Integer32,
				uaxteIpaTemperature
					Integer32,
				uaxteIpaPreAmpCurrent
					Integer32,
				uaxteIpaPallet1Current
					Integer32,
				uaxteIpaPallet2Current
					Integer32,
				uaxteIpaPallet3Current
					Integer32,
				uaxteIpaPallet4Current
					Integer32,
				uaxteIpaPallet5Current
					Integer32,
				uaxteIpaPallet6Current
					Integer32,
				uaxteIpaPallet7Current
					Integer32,
				uaxteIpaPallet8Current
					Integer32,
				uaxteIpaFaultAcMain
					UaxteFaultOk,
				uaxteIpaFaultsRs485Communication
					INTEGER
			 }

		-- 1.3.6.1.4.1.43768.3.1.1.3.2.6.4.1.1.1
		uaxteIpaCabIndex OBJECT-TYPE
			SYNTAX Integer32 (1..8)
			MAX-ACCESS read-only
			STATUS current
			DESCRIPTION
				"Cabinet index in the system MAX is 8 but changes based system configuration"
			::= { uaxteIpaEntry 1 }

		
		-- 1.3.6.1.4.1.43768.3.1.1.3.2.6.4.1.1.2
		uaxteIpaIndex OBJECT-TYPE
			SYNTAX Integer32 (1..2)
			MAX-ACCESS read-only
			STATUS current
			DESCRIPTION
				"IPA Index within the cabinet"
			::= { uaxteIpaEntry 2 }

		
		-- 1.3.6.1.4.1.43768.3.1.1.3.2.6.4.1.1.3
		uaxteIpaOpMode OBJECT-TYPE
			SYNTAX INTEGER
				{
				on(1),
				off(2)
				}
			MAX-ACCESS read-only
			STATUS current
			DESCRIPTION
				"On/Off status of the Pa Module"
			::= { uaxteIpaEntry 3 }

		
		-- 1.3.6.1.4.1.43768.3.1.1.3.2.6.4.1.1.4
		uaxteIpaFwdPwr OBJECT-TYPE
			SYNTAX Integer32
			UNITS "mW"
			MAX-ACCESS read-only
			STATUS current
			DESCRIPTION
				"Forward power of IPA in milliwatts"
			::= { uaxteIpaEntry 4 }

		
		-- 1.3.6.1.4.1.43768.3.1.1.3.2.6.4.1.1.5
		uaxteIpaRfldPwr OBJECT-TYPE
			SYNTAX Integer32
			UNITS "mW"
			MAX-ACCESS read-only
			STATUS current
			DESCRIPTION
				"Reflected power of IPA in milliwatts"
			::= { uaxteIpaEntry 5 }

		
		-- 1.3.6.1.4.1.43768.3.1.1.3.2.6.4.1.1.6
		uaxteIpaVolts OBJECT-TYPE
			SYNTAX Integer32
			UNITS "mV"
			MAX-ACCESS read-only
			STATUS current
			DESCRIPTION
				"DC Volts of IPA in millivolts"
			::= { uaxteIpaEntry 6 }

		
		-- 1.3.6.1.4.1.43768.3.1.1.3.2.6.4.1.1.7
		uaxteIpaTemperature OBJECT-TYPE
			SYNTAX Integer32
			UNITS "C(*0.1)"
			MAX-ACCESS read-only
			STATUS current
			DESCRIPTION
				"take reading and multiple by 0.1 for degree C"
			::= { uaxteIpaEntry 7 }

		
		-- 1.3.6.1.4.1.43768.3.1.1.3.2.6.4.1.1.8
		uaxteIpaPreAmpCurrent OBJECT-TYPE
			SYNTAX Integer32
			UNITS "mA"
			MAX-ACCESS read-only
			STATUS current
			DESCRIPTION
				"not used on some power amplifiers.
				"
			::= { uaxteIpaEntry 8 }

		
		-- 1.3.6.1.4.1.43768.3.1.1.3.2.6.4.1.1.9
		uaxteIpaPallet1Current OBJECT-TYPE
			SYNTAX Integer32
			UNITS "mA"
			MAX-ACCESS read-only
			STATUS current
			DESCRIPTION
				"not used on 2 pallet power amplifiers
				"
			::= { uaxteIpaEntry 9 }

		
		-- 1.3.6.1.4.1.43768.3.1.1.3.2.6.4.1.1.10
		uaxteIpaPallet2Current OBJECT-TYPE
			SYNTAX Integer32
			UNITS "mA"
			MAX-ACCESS read-only
			STATUS current
			DESCRIPTION
				"not used on 1 pallet power amplifiers
				"
			::= { uaxteIpaEntry 10 }

		
		-- 1.3.6.1.4.1.43768.3.1.1.3.2.6.4.1.1.11
		uaxteIpaPallet3Current OBJECT-TYPE
			SYNTAX Integer32
			UNITS "mA"
			MAX-ACCESS read-only
			STATUS current
			DESCRIPTION
				"Description"
			::= { uaxteIpaEntry 11 }

		
		-- 1.3.6.1.4.1.43768.3.1.1.3.2.6.4.1.1.12
		uaxteIpaPallet4Current OBJECT-TYPE
			SYNTAX Integer32
			UNITS "mA"
			MAX-ACCESS read-only
			STATUS current
			DESCRIPTION
				"only used on 4 or more pallet power amplifiers
				"
			::= { uaxteIpaEntry 12 }

		
		-- 1.3.6.1.4.1.43768.3.1.1.3.2.6.4.1.1.13
		uaxteIpaPallet5Current OBJECT-TYPE
			SYNTAX Integer32
			UNITS "mA"
			MAX-ACCESS read-only
			STATUS current
			DESCRIPTION
				"only used on 5 or more pallet power amplifiers
				"
			::= { uaxteIpaEntry 13 }

		
		-- 1.3.6.1.4.1.43768.3.1.1.3.2.6.4.1.1.14
		uaxteIpaPallet6Current OBJECT-TYPE
			SYNTAX Integer32
			UNITS "mA"
			MAX-ACCESS read-only
			STATUS current
			DESCRIPTION
				"only used on 6 or more pallet power amplifiers
				"
			::= { uaxteIpaEntry 14 }

		
		-- 1.3.6.1.4.1.43768.3.1.1.3.2.6.4.1.1.15
		uaxteIpaPallet7Current OBJECT-TYPE
			SYNTAX Integer32
			UNITS "mA"
			MAX-ACCESS read-only
			STATUS current
			DESCRIPTION
				"only used on 7 or more pallet power amplifiers
				"
			::= { uaxteIpaEntry 15 }

		
		-- 1.3.6.1.4.1.43768.3.1.1.3.2.6.4.1.1.16
		uaxteIpaPallet8Current OBJECT-TYPE
			SYNTAX Integer32
			UNITS "mA"
			MAX-ACCESS read-only
			STATUS current
			DESCRIPTION
				"only used on 8 pallet power amplifiers
				"
			::= { uaxteIpaEntry 16 }

		
		-- 1.3.6.1.4.1.43768.3.1.1.3.2.6.4.1.1.17
		uaxteIpaFaultAcMain OBJECT-TYPE
			SYNTAX UaxteFaultOk
			MAX-ACCESS read-only
			STATUS current
			DESCRIPTION
				"AC Main fault of the IPa Module"
			::= { uaxteIpaEntry 17 }

		
		-- 1.3.6.1.4.1.43768.3.1.1.3.2.6.4.1.1.18
		uaxteIpaFaultsRs485Communication OBJECT-TYPE
			SYNTAX INTEGER
				{
				ok(1),
				fail(2)
				}
			MAX-ACCESS read-only
			STATUS current
			DESCRIPTION
				"RS485 communication to the IPa Module"
			::= { uaxteIpaEntry 18 }

		
		-- 1.3.6.1.4.1.43768.3.1.1.3.2.6.5
		uaxtePaDriver OBJECT IDENTIFIER ::= { uaxtePwrAmps 5 }

		
		-- 1.3.6.1.4.1.43768.3.1.1.3.2.6.5.1
		uaxteDriverFwdPwr OBJECT-TYPE
			SYNTAX Integer32
			UNITS "mW"
			MAX-ACCESS read-only
			STATUS current
			DESCRIPTION
				"Forward power of the internal driver."
			::= { uaxtePaDriver 1 }

		
		-- 1.3.6.1.4.1.43768.3.1.1.3.2.6.5.2
		uaxteDriverRfldPwr OBJECT-TYPE
			SYNTAX Integer32
			UNITS "mW"
			MAX-ACCESS read-only
			STATUS current
			DESCRIPTION
				"Reflected power of the internal driver"
			::= { uaxtePaDriver 2 }

		
		-- 1.3.6.1.4.1.43768.3.1.1.3.2.6.5.3
		uaxteDriverInputRms OBJECT-TYPE
			SYNTAX Integer32
			UNITS "uW"
			MAX-ACCESS read-only
			STATUS current
			DESCRIPTION
				"Input power to the internal driver."
			::= { uaxtePaDriver 3 }

		
		-- 1.3.6.1.4.1.43768.3.1.1.3.2.6.5.4
		uaxteDriverCurrent OBJECT-TYPE
			SYNTAX Integer32
			UNITS "mA"
			MAX-ACCESS read-only
			STATUS current
			DESCRIPTION
				"Current reading of the internal driver"
			::= { uaxtePaDriver 4 }

		
		-- 1.3.6.1.4.1.43768.3.1.1.3.2.6.5.5
		uaxteDriverTemperature OBJECT-TYPE
			SYNTAX Integer32
			UNITS "C"
			MAX-ACCESS read-only
			STATUS current
			DESCRIPTION
				"Temperature reading of the internal driver"
			::= { uaxtePaDriver 5 }

		
		-- 1.3.6.1.4.1.43768.3.1.1.3.2.6.5.6
		uaxteDriverVoltage OBJECT-TYPE
			SYNTAX Integer32
			UNITS "mV"
			MAX-ACCESS read-only
			STATUS current
			DESCRIPTION
				"Voltage reading of the internal driver"
			::= { uaxtePaDriver 6 }

		
		-- 1.3.6.1.4.1.43768.3.1.1.3.2.7
		uaxteOutput OBJECT IDENTIFIER ::= { uaxteObjects 7 }

		
		-- 1.3.6.1.4.1.43768.3.1.1.3.2.7.1
		uaxteOutputMeters OBJECT IDENTIFIER ::= { uaxteOutput 1 }

		
		-- 1.3.6.1.4.1.43768.3.1.1.3.2.7.1.1
		uaxteOutputLpuForward OBJECT-TYPE
			SYNTAX Integer32
			UNITS "mW"
			MAX-ACCESS read-only
			STATUS current
			DESCRIPTION
				"Forward power of the low power unit(LPU)."
			::= { uaxteOutputMeters 1 }

		
		-- 1.3.6.1.4.1.43768.3.1.1.3.2.7.1.2
		uaxteOutputLpuReflected OBJECT-TYPE
			SYNTAX Integer32
			UNITS "mW"
			MAX-ACCESS read-only
			STATUS current
			DESCRIPTION
				"Reflected power of the low power unit(LPU)."
			::= { uaxteOutputMeters 2 }

		
		-- 1.3.6.1.4.1.43768.3.1.1.3.2.7.1.3
		uaxteOutputSystemForward OBJECT-TYPE
			SYNTAX Integer32
			UNITS "mW"
			MAX-ACCESS read-only
			STATUS current
			DESCRIPTION
				"Forward power of the system."
			::= { uaxteOutputMeters 3 }

		
		-- 1.3.6.1.4.1.43768.3.1.1.3.2.7.1.4
		uaxteOutputSystemReflected OBJECT-TYPE
			SYNTAX Integer32
			UNITS "mW"
			MAX-ACCESS read-only
			STATUS current
			DESCRIPTION
				"Reflected power of the system."
			::= { uaxteOutputMeters 4 }

		
		-- 1.3.6.1.4.1.43768.3.1.1.3.2.7.2
		uaxteOutputFaults OBJECT IDENTIFIER ::= { uaxteOutput 2 }

		
		-- 1.3.6.1.4.1.43768.3.1.1.3.2.7.2.1
		uaxteOutputForwardLowWarning OBJECT-TYPE
			SYNTAX UaxteWarningOk
			MAX-ACCESS read-only
			STATUS current
			DESCRIPTION
				"Forward power of the system is below the low warning threshold"
			::= { uaxteOutputFaults 1 }

		
		-- 1.3.6.1.4.1.43768.3.1.1.3.2.7.2.2
		uaxteOutputForwardLowFault OBJECT-TYPE
			SYNTAX UaxteFaultOk
			MAX-ACCESS read-only
			STATUS current
			DESCRIPTION
				"Forward power of the system is below the low fault threshold"
			::= { uaxteOutputFaults 2 }

		
		-- 1.3.6.1.4.1.43768.3.1.1.3.2.7.2.3
		uaxteOutputForwardHighFault OBJECT-TYPE
			SYNTAX UaxteFaultOk
			MAX-ACCESS read-only
			STATUS current
			DESCRIPTION
				"Forward power of the system is above high warning threshold"
			::= { uaxteOutputFaults 3 }

		
		-- 1.3.6.1.4.1.43768.3.1.1.3.2.7.2.4
		uaxteOutputMute OBJECT-TYPE
			SYNTAX INTEGER
				{
				muteActive(1),
				muteInactive(2)
				}
			MAX-ACCESS read-write
			STATUS current
			DESCRIPTION
				"Output power of the system is muted."
			::= { uaxteOutputFaults 4 }

		
		-- 1.3.6.1.4.1.43768.3.1.1.3.2.8
		uaxteConfig OBJECT IDENTIFIER ::= { uaxteObjects 8 }

		
		-- 1.3.6.1.4.1.43768.3.1.1.3.2.8.1
		uaxteConfigOuput OBJECT IDENTIFIER ::= { uaxteConfig 1 }

		
		-- 1.3.6.1.4.1.43768.3.1.1.3.2.8.1.1
		uaxteCfgForwardAPCReference OBJECT-TYPE
			SYNTAX Integer32 (0..110)
			UNITS "mW"
			MAX-ACCESS read-write
			STATUS current
			DESCRIPTION
				"The reference power that the transmitter tries to maintain when power control 
				mode is in auto.
				"
			::= { uaxteConfigOuput 1 }

		
		-- 1.3.6.1.4.1.43768.3.1.1.3.2.8.1.2
		uaxteCfgForwardNominal OBJECT-TYPE
			SYNTAX Integer32 (0..100)
			UNITS "mW"
			MAX-ACCESS read-write
			STATUS current
			DESCRIPTION
				"The nominal power reading which represent 100% mark on the GUI."
			::= { uaxteConfigOuput 2 }

		
		-- 1.3.6.1.4.1.43768.3.1.1.3.2.8.1.3
		uaxteCfgForwardLowWarning OBJECT-TYPE
			SYNTAX Integer32 (0..5000)
			UNITS "mV"
			MAX-ACCESS read-write
			STATUS current
			DESCRIPTION
				"The threshold of forward power that triggers the low warning level."
			::= { uaxteConfigOuput 3 }

		
		-- 1.3.6.1.4.1.43768.3.1.1.3.2.8.1.4
		uaxteCfgForwardLowFault OBJECT-TYPE
			SYNTAX Integer32 (0..5000)
			UNITS "mV"
			MAX-ACCESS read-write
			STATUS current
			DESCRIPTION
				"The threshold of forward power that triggers the low fault level."
			::= { uaxteConfigOuput 4 }

		
		-- 1.3.6.1.4.1.43768.3.1.1.3.2.8.1.5
		uaxteCfgForwardHighFault OBJECT-TYPE
			SYNTAX Integer32 (0..100)
			UNITS "mW"
			MAX-ACCESS read-write
			STATUS current
			DESCRIPTION
				"The threshold of forward power that triggers the high warning level."
			::= { uaxteConfigOuput 5 }

		
		-- 1.3.6.1.4.1.43768.3.1.1.3.2.8.1.6
		uaxteCfgRfldFoldbackThreshold OBJECT-TYPE
			SYNTAX Integer32
			UNITS "mW"
			MAX-ACCESS read-write
			STATUS current
			DESCRIPTION
				"The threshold of reflected power that triggers power foldback."
			::= { uaxteConfigOuput 6 }

		
		-- 1.3.6.1.4.1.43768.3.1.1.3.2.8.1.7
		uaxteCfgRfldFault OBJECT-TYPE
			SYNTAX Integer32
			UNITS "mW"
			MAX-ACCESS read-write
			STATUS obsolete
			DESCRIPTION
				"The threshold of reflected power that triggers VSWR protection.
				OBSOLETE only MFG can set this"
			::= { uaxteConfigOuput 7 }

		
		-- 1.3.6.1.4.1.43768.3.1.1.3.2.8.2
		uaxteConfigPowerControl OBJECT IDENTIFIER ::= { uaxteConfig 2 }

		
		-- 1.3.6.1.4.1.43768.3.1.1.3.2.8.2.1
		uaxteCfgPwrCntrlMode OBJECT-TYPE
			SYNTAX UaxteAutoManual
			MAX-ACCESS read-write
			STATUS current
			DESCRIPTION
				"Automatic power control(APC), when in auto the controller will try to
				maintain the the value set by uaxteCfgForwardAPCReference"
			::= { uaxteConfigPowerControl 1 }

		
		-- 1.3.6.1.4.1.43768.3.1.1.3.2.8.2.2
		uaxteCfgPwrCntrlDriveLevel OBJECT-TYPE
			SYNTAX Integer32 (0..1000)
			MAX-ACCESS read-only
			STATUS current
			DESCRIPTION
				"Current APC value. 
				Note when running transmitter at the properly set power the APC value should be above 800"
			::= { uaxteConfigPowerControl 2 }

		
		-- 1.3.6.1.4.1.43768.3.1.1.3.2.8.2.3
		uaxteCfgPwrCntrlDriveLevelAdjust OBJECT-TYPE
			SYNTAX INTEGER
				{
				raise(1),
				lower(2)
				}
			MAX-ACCESS read-write
			STATUS current
			DESCRIPTION
				"Change the power of the transmitter.
				1= increase 2 = descrease. will change the drive level by 10pts
				note after 10 seconds when uaxteCfgPwrCntrlMode = 1(Auto) 
				the uaxteConfigForwardAPCReference will be changed to the transmitters power reading. "
			::= { uaxteConfigPowerControl 3 }

		
		-- 1.3.6.1.4.1.43768.3.1.1.3.2.8.2.4
		uaxteCfgPwrCntrlDriveLimit OBJECT-TYPE
			SYNTAX Integer32 (0..1000)
			MAX-ACCESS read-write
			STATUS current
			DESCRIPTION
				"Max value the Drive level can reach."
			::= { uaxteConfigPowerControl 4 }

		
		-- 1.3.6.1.4.1.43768.3.1.1.3.2.8.2.5
		uaxteCfgPwrCntrlInputAttenuatorLevel OBJECT-TYPE
			SYNTAX Integer32 (0..1000)
			MAX-ACCESS read-write
			STATUS current
			DESCRIPTION
				"Enter the value for attentuor level.
				note the transmitter nominal level for drive level is above 800. 
				By adjusting the Input Attn Level can obtain this value"
			::= { uaxteConfigPowerControl 5 }

		
		-- 1.3.6.1.4.1.43768.3.1.1.3.2.8.2.6
		uaxteCfgPwrCntrlInputAttenuatorLevelAdjust OBJECT-TYPE
			SYNTAX INTEGER
				{
				raise(1),
				lower(2)
				}
			MAX-ACCESS read-write
			STATUS current
			DESCRIPTION
				"Change the Drive Level Input attenuator.
				1= increase 2 = descrease. will change the drive level by 10pts.
				
				note the transmitter nominal level for drive level is above 800. 
				By adjusting the Input Attn Level can obtain this value
				"
			::= { uaxteConfigPowerControl 6 }

		
		-- 1.3.6.1.4.1.43768.3.1.1.3.2.8.3
		uaxteConfigGeneral OBJECT IDENTIFIER ::= { uaxteConfig 3 }

		
		-- 1.3.6.1.4.1.43768.3.1.1.3.2.8.3.1
		uaxteCfgAcRestartDelay OBJECT-TYPE
			SYNTAX Integer32 (0..60)
			UNITS "seconds"
			MAX-ACCESS read-write
			STATUS current
			DESCRIPTION
				"AC restart delay when AC MAin is applied and the operation mode of the
				transmitter was ON prior to AC Main Loss"
			::= { uaxteConfigGeneral 1 }

		
		-- 1.3.6.1.4.1.43768.3.1.1.3.2.9
		uaxteRtac OBJECT IDENTIFIER ::= { uaxteObjects 9 }

		
		-- 1.3.6.1.4.1.43768.3.1.1.3.2.9.1
		uaxteRtacGeneral OBJECT IDENTIFIER ::= { uaxteRtac 1 }

		
		-- 1.3.6.1.4.1.43768.3.1.1.3.2.9.1.1
		uaxteRtacDisabled OBJECT-TYPE
			SYNTAX YesNo
			MAX-ACCESS read-write
			STATUS current
			DESCRIPTION
				"RTAC mode is Enabled/Disabled.
				Note when enabling this control other factors internal to the Transmitter may prevent RTAC from being enabled."
			::= { uaxteRtacGeneral 1 }

		
		-- 1.3.6.1.4.1.43768.3.1.1.3.2.9.2
		uaxteRtacSetup OBJECT IDENTIFIER ::= { uaxteRtac 2 }

		
		-- 1.3.6.1.4.1.43768.3.1.1.3.2.9.2.1
		uaxteRtacSetupPeakReductionMode OBJECT-TYPE
			SYNTAX UaxteAutoManual
			MAX-ACCESS read-write
			STATUS current
			DESCRIPTION
				"1 = AUTO:   Non-Linear Range determined automatically; 
				2 = MANUAL: Non-Linear Range set by datapoint uaxteRtacSetupNonLinearRange"
			::= { uaxteRtacSetup 1 }

		
		-- 1.3.6.1.4.1.43768.3.1.1.3.2.9.2.2
		uaxteRtacSetupNonLinearRange OBJECT-TYPE
			SYNTAX Integer32
			UNITS "dB(*0.1)"
			MAX-ACCESS read-write
			STATUS current
			DESCRIPTION
				"Expected Peak-to-average ratio of the waveform after the PA."
			::= { uaxteRtacSetup 2 }

		
		-- 1.3.6.1.4.1.43768.3.1.1.3.2.9.2.3
		uaxteRtacSetupMaxCrestFactor OBJECT-TYPE
			SYNTAX Integer32
			UNITS "dB(*0.1)"
			MAX-ACCESS read-write
			STATUS current
			DESCRIPTION
				"Limit on the Peak-to-average ratio of the transmitter output with peak expansion"
			::= { uaxteRtacSetup 3 }

		
		-- 1.3.6.1.4.1.43768.3.1.1.3.2.9.3
		uaxteRtacLinear OBJECT IDENTIFIER ::= { uaxteRtac 3 }

		
		-- 1.3.6.1.4.1.43768.3.1.1.3.2.9.3.1
		uaxteRtacLinearMode OBJECT-TYPE
			SYNTAX INTEGER
				{
				adapt(1),
				bypass(2),
				hold(3),
				stored(4)
				}
			MAX-ACCESS read-write
			STATUS current
			DESCRIPTION
				"Rtac Linear Mode of operation"
			::= { uaxteRtacLinear 1 }

		
		-- 1.3.6.1.4.1.43768.3.1.1.3.2.9.3.2
		uaxteRtacLinearSuccess OBJECT-TYPE
			SYNTAX Integer32
			MAX-ACCESS read-only
			STATUS current
			DESCRIPTION
				"Rtac Linear successful attempts of adaption"
			::= { uaxteRtacLinear 2 }

		
		-- 1.3.6.1.4.1.43768.3.1.1.3.2.9.3.3
		uaxteRtacLinearAttempts OBJECT-TYPE
			SYNTAX Integer32
			MAX-ACCESS read-only
			STATUS current
			DESCRIPTION
				"Rtac Linear attempts of adaption"
			::= { uaxteRtacLinear 3 }

		
		-- 1.3.6.1.4.1.43768.3.1.1.3.2.9.3.4
		uaxteRtacLinearModeAfterAcLoss OBJECT-TYPE
			SYNTAX INTEGER
				{
				adapt(1),
				bypass(2),
				hold(3),
				stored(4),
				auto(5),
				current(7)
				}
			MAX-ACCESS read-write
			STATUS current
			DESCRIPTION
				"Rtac Linear Mode of operation after AC Loss"
			::= { uaxteRtacLinear 4 }

		
		-- 1.3.6.1.4.1.43768.3.1.1.3.2.9.4
		uaxteRtacNonLinear OBJECT IDENTIFIER ::= { uaxteRtac 4 }

		
		-- 1.3.6.1.4.1.43768.3.1.1.3.2.9.4.1
		uaxteRtacNonLinearMode OBJECT-TYPE
			SYNTAX INTEGER
				{
				adapt(1),
				bypass(2),
				hold(3),
				stored(4)
				}
			MAX-ACCESS read-write
			STATUS current
			DESCRIPTION
				"Rtac NonLinear Mode of operation"
			::= { uaxteRtacNonLinear 1 }

		
		-- 1.3.6.1.4.1.43768.3.1.1.3.2.9.4.2
		uaxteRtacNonLinearSuccess OBJECT-TYPE
			SYNTAX Integer32
			MAX-ACCESS read-only
			STATUS current
			DESCRIPTION
				"Rtac NonLinear successful attempts of adaption"
			::= { uaxteRtacNonLinear 2 }

		
		-- 1.3.6.1.4.1.43768.3.1.1.3.2.9.4.3
		uaxteRtacNonLinearAttempts OBJECT-TYPE
			SYNTAX Integer32
			MAX-ACCESS read-only
			STATUS current
			DESCRIPTION
				"Rtac NonLinear attempts of adaption"
			::= { uaxteRtacNonLinear 3 }

		
		-- 1.3.6.1.4.1.43768.3.1.1.3.2.9.4.4
		uaxteRtacNonLinearModeAfterAcLoss OBJECT-TYPE
			SYNTAX INTEGER
				{
				adapt(1),
				bypass(2),
				hold(3),
				stored(4),
				auto(5),
				current(7)
				}
			MAX-ACCESS read-write
			STATUS current
			DESCRIPTION
				"Rtac NonLinear Mode of operation after AC Loss"
			::= { uaxteRtacNonLinear 4 }

		
		-- 1.3.6.1.4.1.43768.3.1.1.3.2.9.5
		uaxteRtacPerformance OBJECT IDENTIFIER ::= { uaxteRtac 5 }

		
		-- 1.3.6.1.4.1.43768.3.1.1.3.2.9.5.1
		uaxteRtacPerfLSB OBJECT-TYPE
			SYNTAX Integer32
			UNITS "mdB"
			MAX-ACCESS read-only
			STATUS current
			DESCRIPTION
				"Lower sideband(LSB) value
				Example Value -30472 = -30.472dB"
			::= { uaxteRtacPerformance 1 }

		
		-- 1.3.6.1.4.1.43768.3.1.1.3.2.9.5.2
		uaxteRtacPerfUSB OBJECT-TYPE
			SYNTAX Integer32
			UNITS "mdB"
			MAX-ACCESS read-only
			STATUS current
			DESCRIPTION
				"Upper sideband(USB) value
				Example Value -30472 = -30.472dB"
			::= { uaxteRtacPerformance 2 }

		
		-- 1.3.6.1.4.1.43768.3.1.1.3.2.9.5.3
		uaxteRtacPerfEVM OBJECT-TYPE
			SYNTAX Integer32
			UNITS "m%"
			MAX-ACCESS read-only
			STATUS current
			DESCRIPTION
				"Example Value 1000 = 1%"
			::= { uaxteRtacPerformance 3 }

		
		-- 1.3.6.1.4.1.43768.3.1.1.3.2.9.5.4
		uaxteRtacPerfMERSNR OBJECT-TYPE
			SYNTAX Integer32
			UNITS "mdB"
			MAX-ACCESS read-only
			STATUS current
			DESCRIPTION
				"SNR for ATSC Modulation, MER for all others
				Example Value -30472 = -30.472dB"
			::= { uaxteRtacPerformance 4 }

		
		-- 1.3.6.1.4.1.43768.3.1.1.3.2.9.5.5
		uaxteRtacPerfValid OBJECT-TYPE
			SYNTAX YesNo
			MAX-ACCESS read-only
			STATUS current
			DESCRIPTION
				"if value = 2(No) then that RTAC performance readings are invalid, 
				the RTAC performance numbers are only updated when a valid signal 
				is present on the pre/post filter inputs"
			::= { uaxteRtacPerformance 5 }

		
		-- 1.3.6.1.4.1.43768.3.1.1.3.2.10
		uaxtePowerSupplies OBJECT IDENTIFIER ::= { uaxteObjects 10 }

		
		-- 1.3.6.1.4.1.43768.3.1.1.3.2.10.1
		uaxtePwrSupplyController OBJECT-TYPE
			SYNTAX UaxteSummaryStatus
			MAX-ACCESS read-only
			STATUS current
			DESCRIPTION
				"Transmitters power supply controller status."
			::= { uaxtePowerSupplies 1 }

		
		-- 1.3.6.1.4.1.43768.3.1.1.3.2.10.2
		uaxtePwrSupplyPwrAmp OBJECT-TYPE
			SYNTAX UaxteSummaryStatus
			MAX-ACCESS read-only
			STATUS current
			DESCRIPTION
				"Transmitters power supply power amplifier status."
			::= { uaxtePowerSupplies 2 }

		
		-- 1.3.6.1.4.1.43768.3.1.1.3.2.10.3
		uaxtePwrSupplyModulator OBJECT-TYPE
			SYNTAX UaxteSummaryStatus
			MAX-ACCESS read-only
			STATUS current
			DESCRIPTION
				"Transmitters power supply modulator status."
			::= { uaxtePowerSupplies 3 }

		
		-- 1.3.6.1.4.1.43768.3.1.1.3.2.11
		uaxteCooling OBJECT IDENTIFIER ::= { uaxteObjects 11 }

		
		-- 1.3.6.1.4.1.43768.3.1.1.3.2.11.1
		uaxteCoolingTempAmbient OBJECT-TYPE
			SYNTAX Integer32
			UNITS "deg C"
			MAX-ACCESS read-only
			STATUS current
			DESCRIPTION
				"Ambient temperature reading."
			::= { uaxteCooling 1 }

		
		-- 1.3.6.1.4.1.43768.3.1.1.3.2.11.2
		uaxteCoolingTempPwrAmp OBJECT-TYPE
			SYNTAX Integer32
			UNITS "deg C"
			MAX-ACCESS read-only
			STATUS current
			DESCRIPTION
				"Power amplifier temperature reading."
			::= { uaxteCooling 2 }

		
		-- 1.3.6.1.4.1.43768.3.1.1.3.2.11.3
		uaxteCoolingTempFpga1 OBJECT-TYPE
			SYNTAX Integer32
			UNITS "deg C"
			MAX-ACCESS read-only
			STATUS current
			DESCRIPTION
				"Fpga1 internal temperature reading."
			::= { uaxteCooling 3 }

		
		-- 1.3.6.1.4.1.43768.3.1.1.3.2.11.4
		uaxteCoolingTempFpga2 OBJECT-TYPE
			SYNTAX Integer32
			UNITS "deg C"
			MAX-ACCESS read-only
			STATUS current
			DESCRIPTION
				"Fpga2 internal temperature reading.
				Note: not always used."
			::= { uaxteCooling 4 }

		
		-- 1.3.6.1.4.1.43768.3.1.1.3.2.11.5
		uaxteKernelTemp OBJECT-TYPE
			SYNTAX Integer32
			MAX-ACCESS read-write
			STATUS current
			DESCRIPTION
				"Kernel internal temperature reading."
			::= { uaxteCooling 5 }

		
		-- 1.3.6.1.4.1.43768.3.1.1.3.2.11.6
		uaxteCoolingTempBattery OBJECT-TYPE
			SYNTAX Integer32
			UNITS "deg C"
			MAX-ACCESS read-only
			STATUS current
			DESCRIPTION
				"External battery temperature reading.
				Note: not always used."
			::= { uaxteCooling 6 }

		
		-- 1.3.6.1.4.1.43768.3.1.1.3.2.11.7
		uaxteCoolingRpmFan1 OBJECT-TYPE
			SYNTAX Integer32
			UNITS "rpm"
			MAX-ACCESS read-only
			STATUS current
			DESCRIPTION
				"RPMs of fan1"
			::= { uaxteCooling 7 }

		
		-- 1.3.6.1.4.1.43768.3.1.1.3.2.11.8
		uaxteCoolingRpmFan2 OBJECT-TYPE
			SYNTAX Integer32
			UNITS "rpm"
			MAX-ACCESS read-only
			STATUS current
			DESCRIPTION
				"RPMs of fan2"
			::= { uaxteCooling 8 }

		
		-- 1.3.6.1.4.1.43768.3.1.1.3.2.11.9
		uaxteCoolingRpmFan3 OBJECT-TYPE
			SYNTAX Integer32
			UNITS "rpm"
			MAX-ACCESS read-only
			STATUS current
			DESCRIPTION
				"RPMs of fan3, note used in all UAXTE types"
			::= { uaxteCooling 9 }

		
		-- 1.3.6.1.4.1.43768.3.1.1.3.2.11.10
		uaxteCoolingRpmFan4 OBJECT-TYPE
			SYNTAX Integer32
			UNITS "rpm"
			MAX-ACCESS read-only
			STATUS current
			DESCRIPTION
				"RPMs of fan4. note used in all UAXTE types"
			::= { uaxteCooling 10 }

		
		-- 1.3.6.1.4.1.43768.3.1.1.3.2.12
		uaxteNetwork OBJECT IDENTIFIER ::= { uaxteObjects 12 }

		
		-- 1.3.6.1.4.1.43768.3.1.1.3.2.12.1
		uaxteNetworkTable OBJECT-TYPE
			SYNTAX SEQUENCE OF UaxteNetworkEntry
			MAX-ACCESS not-accessible
			STATUS current
			DESCRIPTION
				"Description."
			::= { uaxteNetwork 1 }

		
		-- 1.3.6.1.4.1.43768.3.1.1.3.2.12.1.1
		uaxteNetworkEntry OBJECT-TYPE
			SYNTAX UaxteNetworkEntry
			MAX-ACCESS not-accessible
			STATUS current
			DESCRIPTION
				"Description."
			INDEX { uaxteNetworkIndex }
			::= { uaxteNetworkTable 1 }

		
		UaxteNetworkEntry ::=
			SEQUENCE { 
				uaxteNetworkIndex
					INTEGER,
				uaxteNetworkMac
					OCTET STRING,
				uaxteNetworkAddr
					IpAddress,
				uaxteNetworkNetmask
					IpAddress,
				uaxteNetworkLink
					YesNo,
				uaxteNetworkDuplexMode
					UaxteNetworkDuplex,
				uaxteNetworkSpeed
					Integer32,
				uaxteNetworkAutoNegotiate
					UaxteAutoManual
			 }

		-- 1.3.6.1.4.1.43768.3.1.1.3.2.12.1.1.1
		uaxteNetworkIndex OBJECT-TYPE
			SYNTAX INTEGER
				{
				wan(1),
				lan(2),
				dtiip1(3),
				dtiip2(4)
				}
			MAX-ACCESS read-only
			STATUS current
			DESCRIPTION
				"Description."
			::= { uaxteNetworkEntry 1 }

		
		-- 1.3.6.1.4.1.43768.3.1.1.3.2.12.1.1.2
		uaxteNetworkMac OBJECT-TYPE
			SYNTAX OCTET STRING
			MAX-ACCESS read-only
			STATUS current
			DESCRIPTION
				"MAC address of the given interface"
			::= { uaxteNetworkEntry 2 }

		
		-- 1.3.6.1.4.1.43768.3.1.1.3.2.12.1.1.3
		uaxteNetworkAddr OBJECT-TYPE
			SYNTAX IpAddress
			MAX-ACCESS read-only
			STATUS current
			DESCRIPTION
				"IP address of the given interface"
			::= { uaxteNetworkEntry 3 }

		
		-- 1.3.6.1.4.1.43768.3.1.1.3.2.12.1.1.4
		uaxteNetworkNetmask OBJECT-TYPE
			SYNTAX IpAddress
			MAX-ACCESS read-only
			STATUS current
			DESCRIPTION
				"Netmask of the given interface"
			::= { uaxteNetworkEntry 4 }

		
		-- 1.3.6.1.4.1.43768.3.1.1.3.2.12.1.1.5
		uaxteNetworkLink OBJECT-TYPE
			SYNTAX YesNo
			MAX-ACCESS read-only
			STATUS current
			DESCRIPTION
				"Status of the given interface is connected to a network"
			::= { uaxteNetworkEntry 5 }

		
		-- 1.3.6.1.4.1.43768.3.1.1.3.2.12.1.1.6
		uaxteNetworkDuplexMode OBJECT-TYPE
			SYNTAX UaxteNetworkDuplex
			MAX-ACCESS read-only
			STATUS current
			DESCRIPTION
				"Duplex mode of the given interface"
			::= { uaxteNetworkEntry 6 }

		
		-- 1.3.6.1.4.1.43768.3.1.1.3.2.12.1.1.7
		uaxteNetworkSpeed OBJECT-TYPE
			SYNTAX Integer32
			MAX-ACCESS read-only
			STATUS current
			DESCRIPTION
				"Network speed of the given interface"
			::= { uaxteNetworkEntry 7 }

		
		-- 1.3.6.1.4.1.43768.3.1.1.3.2.12.1.1.8
		uaxteNetworkAutoNegotiate OBJECT-TYPE
			SYNTAX UaxteAutoManual
			MAX-ACCESS read-only
			STATUS current
			DESCRIPTION
				"Auto negotiate mode of the given interface"
			::= { uaxteNetworkEntry 8 }

		
		-- 1.3.6.1.4.1.43768.3.1.1.3.2.12.2
		uaxteInputNetworkTable OBJECT-TYPE
			SYNTAX SEQUENCE OF UaxteInputNetworkEntry
			MAX-ACCESS not-accessible
			STATUS current
			DESCRIPTION
				"Description."
			::= { uaxteNetwork 2 }

		
		-- 1.3.6.1.4.1.43768.3.1.1.3.2.12.2.1
		uaxteInputNetworkEntry OBJECT-TYPE
			SYNTAX UaxteInputNetworkEntry
			MAX-ACCESS not-accessible
			STATUS current
			DESCRIPTION
				"Description."
			INDEX { uaxteInputNetworkIndex }
			::= { uaxteInputNetworkTable 1 }

		
		UaxteInputNetworkEntry ::=
			SEQUENCE { 
				uaxteInputNetworkIndex
					INTEGER,
				uaxteInputNetworkMode
					INTEGER,
				uaxteInputNetworkDestAddress
					IpAddress,
				uaxteInputNetworkDestPort
					Integer32,
				uaxteInputNetworkSourceFilter
					EnabledDisabled,
				uaxteInputNetworkSourceAddress
					IpAddress,
				uaxteInputNetworkSourcePort
					Integer32,
				uaxteInputNetworkSMPTE2022Mode
					INTEGER,
				uaxteInputNetworkRxBytes
					Integer32,
				uaxteInputNetworkRxFrames
					Integer32,
				uaxteInputNetworkTxBytes
					Integer32,
				uaxteInputNetworkTxFrames
					Integer32,
				uaxteInputNetworkIGMPRequest
					Integer32,
				uaxteInputNetworkIGMPReports
					Integer32,
				uaxteInputNetworkUDPReceived
					Integer32,
				uaxteInputNetworkUDPDiscarded
					Integer32,
				uaxteInputNetworkUDPErrors
					Integer32,
				uaxteInputNetworkResetStats
					INTEGER,
				uaxteInputNetworkFecRecoved
					Integer32,
				uaxteInputNetworkFecLost
					Integer32,
				uaxteInputNetworkFecLValue
					Integer32,
				uaxteInputNetworkFecDValue
					Integer32,
				uaxteInputNetworkFecResetStats
					INTEGER
			 }

		-- 1.3.6.1.4.1.43768.3.1.1.3.2.12.2.1.1
		uaxteInputNetworkIndex OBJECT-TYPE
			SYNTAX INTEGER
				{
				dti1(1),
				dti2(2)
				}
			MAX-ACCESS read-write
			STATUS current
			DESCRIPTION
				"Description."
			::= { uaxteInputNetworkEntry 1 }

		
		-- 1.3.6.1.4.1.43768.3.1.1.3.2.12.2.1.2
		uaxteInputNetworkMode OBJECT-TYPE
			SYNTAX INTEGER
				{
				multicast(1),
				unicast(2)
				}
			MAX-ACCESS read-only
			STATUS current
			DESCRIPTION
				"Description."
			::= { uaxteInputNetworkEntry 2 }

		
		-- 1.3.6.1.4.1.43768.3.1.1.3.2.12.2.1.3
		uaxteInputNetworkDestAddress OBJECT-TYPE
			SYNTAX IpAddress
			MAX-ACCESS read-only
			STATUS current
			DESCRIPTION
				"Description."
			::= { uaxteInputNetworkEntry 3 }

		
		-- 1.3.6.1.4.1.43768.3.1.1.3.2.12.2.1.4
		uaxteInputNetworkDestPort OBJECT-TYPE
			SYNTAX Integer32
			MAX-ACCESS read-only
			STATUS current
			DESCRIPTION
				"Description."
			::= { uaxteInputNetworkEntry 4 }

		
		-- 1.3.6.1.4.1.43768.3.1.1.3.2.12.2.1.5
		uaxteInputNetworkSourceFilter OBJECT-TYPE
			SYNTAX EnabledDisabled
			MAX-ACCESS read-only
			STATUS current
			DESCRIPTION
				"Description."
			::= { uaxteInputNetworkEntry 5 }

		
		-- 1.3.6.1.4.1.43768.3.1.1.3.2.12.2.1.6
		uaxteInputNetworkSourceAddress OBJECT-TYPE
			SYNTAX IpAddress
			MAX-ACCESS read-only
			STATUS current
			DESCRIPTION
				"Description."
			::= { uaxteInputNetworkEntry 6 }

		
		-- 1.3.6.1.4.1.43768.3.1.1.3.2.12.2.1.7
		uaxteInputNetworkSourcePort OBJECT-TYPE
			SYNTAX Integer32
			MAX-ACCESS read-only
			STATUS current
			DESCRIPTION
				"Description."
			::= { uaxteInputNetworkEntry 7 }

		
		-- 1.3.6.1.4.1.43768.3.1.1.3.2.12.2.1.8
		uaxteInputNetworkSMPTE2022Mode OBJECT-TYPE
			SYNTAX INTEGER
				{
				none(1),
				fec1D(2),
				fec2D(3)
				}
			MAX-ACCESS read-only
			STATUS current
			DESCRIPTION
				"Description."
			::= { uaxteInputNetworkEntry 8 }

		
		-- 1.3.6.1.4.1.43768.3.1.1.3.2.12.2.1.9
		uaxteInputNetworkRxBytes OBJECT-TYPE
			SYNTAX Integer32
			MAX-ACCESS read-only
			STATUS current
			DESCRIPTION
				"Description."
			::= { uaxteInputNetworkEntry 9 }

		
		-- 1.3.6.1.4.1.43768.3.1.1.3.2.12.2.1.10
		uaxteInputNetworkRxFrames OBJECT-TYPE
			SYNTAX Integer32
			MAX-ACCESS read-only
			STATUS current
			DESCRIPTION
				"Description."
			::= { uaxteInputNetworkEntry 10 }

		
		-- 1.3.6.1.4.1.43768.3.1.1.3.2.12.2.1.11
		uaxteInputNetworkTxBytes OBJECT-TYPE
			SYNTAX Integer32
			MAX-ACCESS read-only
			STATUS current
			DESCRIPTION
				"Description."
			::= { uaxteInputNetworkEntry 11 }

		
		-- 1.3.6.1.4.1.43768.3.1.1.3.2.12.2.1.12
		uaxteInputNetworkTxFrames OBJECT-TYPE
			SYNTAX Integer32
			MAX-ACCESS read-only
			STATUS current
			DESCRIPTION
				"Description."
			::= { uaxteInputNetworkEntry 12 }

		
		-- 1.3.6.1.4.1.43768.3.1.1.3.2.12.2.1.13
		uaxteInputNetworkIGMPRequest OBJECT-TYPE
			SYNTAX Integer32
			MAX-ACCESS read-only
			STATUS current
			DESCRIPTION
				"Description."
			::= { uaxteInputNetworkEntry 13 }

		
		-- 1.3.6.1.4.1.43768.3.1.1.3.2.12.2.1.14
		uaxteInputNetworkIGMPReports OBJECT-TYPE
			SYNTAX Integer32
			MAX-ACCESS read-only
			STATUS current
			DESCRIPTION
				"Description."
			::= { uaxteInputNetworkEntry 14 }

		
		-- 1.3.6.1.4.1.43768.3.1.1.3.2.12.2.1.15
		uaxteInputNetworkUDPReceived OBJECT-TYPE
			SYNTAX Integer32
			MAX-ACCESS read-only
			STATUS current
			DESCRIPTION
				"Description."
			::= { uaxteInputNetworkEntry 15 }

		
		-- 1.3.6.1.4.1.43768.3.1.1.3.2.12.2.1.16
		uaxteInputNetworkUDPDiscarded OBJECT-TYPE
			SYNTAX Integer32
			MAX-ACCESS read-only
			STATUS current
			DESCRIPTION
				"Description."
			::= { uaxteInputNetworkEntry 16 }

		
		-- 1.3.6.1.4.1.43768.3.1.1.3.2.12.2.1.17
		uaxteInputNetworkUDPErrors OBJECT-TYPE
			SYNTAX Integer32
			MAX-ACCESS read-only
			STATUS current
			DESCRIPTION
				"Description."
			::= { uaxteInputNetworkEntry 17 }

		
		-- 1.3.6.1.4.1.43768.3.1.1.3.2.12.2.1.18
		uaxteInputNetworkResetStats OBJECT-TYPE
			SYNTAX INTEGER
				{
				clearDti1(1),
				clearDti2(2)
				}
			MAX-ACCESS read-write
			STATUS current
			DESCRIPTION
				"Description."
			::= { uaxteInputNetworkEntry 18 }

		
		-- 1.3.6.1.4.1.43768.3.1.1.3.2.12.2.1.19
		uaxteInputNetworkFecRecoved OBJECT-TYPE
			SYNTAX Integer32
			MAX-ACCESS read-only
			STATUS current
			DESCRIPTION
				"Description."
			::= { uaxteInputNetworkEntry 19 }

		
		-- 1.3.6.1.4.1.43768.3.1.1.3.2.12.2.1.20
		uaxteInputNetworkFecLost OBJECT-TYPE
			SYNTAX Integer32
			MAX-ACCESS read-only
			STATUS current
			DESCRIPTION
				"Description."
			::= { uaxteInputNetworkEntry 20 }

		
		-- 1.3.6.1.4.1.43768.3.1.1.3.2.12.2.1.21
		uaxteInputNetworkFecLValue OBJECT-TYPE
			SYNTAX Integer32
			MAX-ACCESS read-only
			STATUS current
			DESCRIPTION
				"Description."
			::= { uaxteInputNetworkEntry 21 }

		
		-- 1.3.6.1.4.1.43768.3.1.1.3.2.12.2.1.22
		uaxteInputNetworkFecDValue OBJECT-TYPE
			SYNTAX Integer32
			MAX-ACCESS read-only
			STATUS current
			DESCRIPTION
				"Description."
			::= { uaxteInputNetworkEntry 22 }

		
		-- 1.3.6.1.4.1.43768.3.1.1.3.2.12.2.1.23
		uaxteInputNetworkFecResetStats OBJECT-TYPE
			SYNTAX INTEGER
				{
				clearDti1(1),
				clearDti2(2)
				}
			MAX-ACCESS read-write
			STATUS current
			DESCRIPTION
				"Description."
			::= { uaxteInputNetworkEntry 23 }

		
		-- 1.3.6.1.4.1.43768.3.1.1.3.2.13
		uaxteFTR OBJECT IDENTIFIER ::= { uaxteObjects 13 }

		
		-- 1.3.6.1.4.1.43768.3.1.1.3.2.13.1
		uaxteFtrOcxo OBJECT IDENTIFIER ::= { uaxteFTR 1 }

		
		-- 1.3.6.1.4.1.43768.3.1.1.3.2.13.1.1
		uaxteOcxoReferenceSystem OBJECT-TYPE
			SYNTAX INTEGER
				{
				gps(1),
				euaxternalREF(2),
				manual(3),
				auto1PPS(4)
				}
			MAX-ACCESS read-write
			STATUS current
			DESCRIPTION
				"OCXO System Reference, "
			::= { uaxteFtrOcxo 1 }

		
		-- 1.3.6.1.4.1.43768.3.1.1.3.2.13.1.2
		uaxteOcxoTuning OBJECT-TYPE
			SYNTAX Integer32
			MAX-ACCESS read-write
			STATUS current
			DESCRIPTION
				"OCXO Tuning
				Note only used when uaxteOcxoReferenceSystem = Manual."
			::= { uaxteFtrOcxo 2 }

		
		-- 1.3.6.1.4.1.43768.3.1.1.3.2.13.1.3
		uaxteOcxoRfOutIfUndisciplined OBJECT-TYPE
			SYNTAX YesNo
			MAX-ACCESS read-write
			STATUS current
			DESCRIPTION
				"If undisciplined then the RF will be muted
				NOTE: this does not apply to DVBT2"
			::= { uaxteFtrOcxo 3 }

		
		-- 1.3.6.1.4.1.43768.3.1.1.3.2.13.1.4
		uaxteOcxo1ppsInputPrimary OBJECT-TYPE
			SYNTAX INTEGER
				{
				internalGPS(1),
				euaxternalGPS(2)
				}
			MAX-ACCESS read-write
			STATUS current
			DESCRIPTION
				"FTR 1PPS Primary selection, Only valid when uaxteOcxoReferenceSystem = Auto1PPS"
			::= { uaxteFtrOcxo 4 }

		
		-- 1.3.6.1.4.1.43768.3.1.1.3.2.13.1.5
		uaxteOcxo1ppsInputActual OBJECT-TYPE
			SYNTAX INTEGER
				{
				internalGPS(1),
				externalGPS(2)
				}
			MAX-ACCESS read-write
			STATUS current
			DESCRIPTION
				"FTR 1PPS actual selection, Only valid when uaxteOcxoReferenceSystem = Auto1PPS"
			::= { uaxteFtrOcxo 5 }

		
		-- 1.3.6.1.4.1.43768.3.1.1.3.2.13.1.6
		uaxteOcxoGnssMode OBJECT-TYPE
			SYNTAX INTEGER
				{
				gps(1),
				glonass(2)
				}
			MAX-ACCESS read-write
			STATUS current
			DESCRIPTION
				"GNSS mode"
			::= { uaxteFtrOcxo 6 }

		
		-- 1.3.6.1.4.1.43768.3.1.1.3.2.13.1.7
		uaxteOcxoReferenceInput OBJECT-TYPE
			SYNTAX INTEGER
				{
				none(1),
				ext1PPS(2),
				ext10MHz(3)
				}
			MAX-ACCESS read-write
			STATUS current
			DESCRIPTION
				"Reference input selection"
			::= { uaxteFtrOcxo 7 }

		
		-- 1.3.6.1.4.1.43768.3.1.1.3.2.13.1.8
		uaxteOcxoReferenceInputTermination OBJECT-TYPE
			SYNTAX INTEGER
				{
				ohm50(1),
				ohm10K(2)
				}
			MAX-ACCESS read-write
			STATUS current
			DESCRIPTION
				"Reference input termination."
			::= { uaxteFtrOcxo 8 }

		
		-- 1.3.6.1.4.1.43768.3.1.1.3.2.13.1.9
		uaxteOcxoReferenceOutput OBJECT-TYPE
			SYNTAX INTEGER
				{
				none(1),
				gps1PPS(2),
				synthesized1PPS(3),
				tenMHz(4)
				}
			MAX-ACCESS read-write
			STATUS current
			DESCRIPTION
				"Reference output selection"
			::= { uaxteFtrOcxo 9 }

		
		-- 1.3.6.1.4.1.43768.3.1.1.3.2.13.1.10
		uaxteOcxoReferenceLossMute OBJECT-TYPE
			SYNTAX INTEGER
				{
				noMute(1),
				muteImmediatly(2),
				guardIntervalExceeds20Percent(3),
				timeoutExceeded(4)
				}
			MAX-ACCESS read-write
			STATUS current
			DESCRIPTION
				"NOTE: this only applies for DVB-T and DVB-T2"
			::= { uaxteFtrOcxo 10 }

		
		-- 1.3.6.1.4.1.43768.3.1.1.3.2.13.1.11
		uaxteOcxoReferenceTimeout OBJECT-TYPE
			SYNTAX Integer32 (0..8)
			UNITS "hours"
			MAX-ACCESS read-write
			STATUS current
			DESCRIPTION
				"NOTE: this only applies for DVB-T and DVB-T2"
			::= { uaxteFtrOcxo 11 }

		
		-- 1.3.6.1.4.1.43768.3.1.1.3.2.13.2
		uaxteFtrReadiness OBJECT-TYPE
			SYNTAX Integer32
			UNITS "%"
			MAX-ACCESS read-only
			STATUS current
			DESCRIPTION
				"Frequency timing reference status, Readiness of the exciter.."
			::= { uaxteFTR 2 }

		
		-- 1.3.6.1.4.1.43768.3.1.1.3.2.13.3
		uaxteFtrTimeRemaining OBJECT-TYPE
			SYNTAX Integer32
			UNITS "seconds"
			MAX-ACCESS read-only
			STATUS current
			DESCRIPTION
				"Frequency timing reference status, Time remaining once system reference signal 
				is lost to be within 20uS error of reference 1PPS."
			::= { uaxteFTR 3 }

		
		-- 1.3.6.1.4.1.43768.3.1.1.3.2.13.4
		uaxteFtrSystemRefInput OBJECT-TYPE
			SYNTAX UaxteFtrReferenceStatus
			MAX-ACCESS read-only
			STATUS current
			DESCRIPTION
				"Frequency timing reference status, System reference input status."
			::= { uaxteFTR 4 }

		
		-- 1.3.6.1.4.1.43768.3.1.1.3.2.13.5
		uaxteFtrSystemRefIntGps1pps OBJECT-TYPE
			SYNTAX UaxteFtrReferenceStatus
			MAX-ACCESS read-only
			STATUS current
			DESCRIPTION
				"Frequency timing reference status, System Reference internal GPS 1PPS status "
			::= { uaxteFTR 5 }

		
		-- 1.3.6.1.4.1.43768.3.1.1.3.2.13.6
		uaxteFtrPllRefClock OBJECT-TYPE
			SYNTAX UaxtePllStatus
			MAX-ACCESS read-only
			STATUS current
			DESCRIPTION
				"Frequency timing reference status, PLL reference clock 100MHz  "
			::= { uaxteFTR 6 }

		
		-- 1.3.6.1.4.1.43768.3.1.1.3.2.13.7
		uaxteFtrPllLockRfLo1 OBJECT-TYPE
			SYNTAX UaxtePllStatus
			MAX-ACCESS read-only
			STATUS current
			DESCRIPTION
				"Frequency timing reference status, RF LO 1 lock status."
			::= { uaxteFTR 7 }

		
		-- 1.3.6.1.4.1.43768.3.1.1.3.2.13.8
		uaxteFtrPllLockRfLo2 OBJECT-TYPE
			SYNTAX UaxtePllStatus
			MAX-ACCESS read-only
			STATUS current
			DESCRIPTION
				"Frequency timing reference status, RF LO 2 lock status."
			::= { uaxteFTR 8 }

		
		-- 1.3.6.1.4.1.43768.3.1.1.3.2.13.9
		uaxteFtrPllLockDigital OBJECT-TYPE
			SYNTAX UaxtePllStatus
			MAX-ACCESS read-only
			STATUS current
			DESCRIPTION
				"Frequency timing reference status, Digital lock status."
			::= { uaxteFTR 9 }

		
		-- 1.3.6.1.4.1.43768.3.1.1.3.2.13.10
		uaxteFtrFrequency OBJECT-TYPE
			SYNTAX Integer32
			UNITS "hz"
			MAX-ACCESS read-write
			STATUS current
			DESCRIPTION
				"The frequency of the Transmiiter in hz."
			::= { uaxteFTR 10 }

		
		-- 1.3.6.1.4.1.43768.3.1.1.3.2.14
		uaxteGpsGnss OBJECT IDENTIFIER ::= { uaxteObjects 14 }

		
		-- 1.3.6.1.4.1.43768.3.1.1.3.2.14.1
		uaxteGpsGnssNumberofSatellites OBJECT-TYPE
			SYNTAX Integer32
			MAX-ACCESS read-only
			STATUS current
			DESCRIPTION
				"The number of satellites detected"
			::= { uaxteGpsGnss 1 }

		
		-- 1.3.6.1.4.1.43768.3.1.1.3.2.14.2
		uaxteGpsGnssSatelliteTime OBJECT-TYPE
			SYNTAX OCTET STRING
			MAX-ACCESS read-only
			STATUS current
			DESCRIPTION
				"Satellite Time"
			::= { uaxteGpsGnss 2 }

		
		-- 1.3.6.1.4.1.43768.3.1.1.3.2.14.3
		uaxteGpsGnssLatitude OBJECT-TYPE
			SYNTAX OCTET STRING
			MAX-ACCESS read-only
			STATUS current
			DESCRIPTION
				"Latitude Reading"
			::= { uaxteGpsGnss 3 }

		
		-- 1.3.6.1.4.1.43768.3.1.1.3.2.14.4
		uaxteGpsGnssLongitude OBJECT-TYPE
			SYNTAX OCTET STRING
			MAX-ACCESS read-only
			STATUS current
			DESCRIPTION
				"Description."
			::= { uaxteGpsGnss 4 }

		
		-- 1.3.6.1.4.1.43768.3.1.1.3.2.14.5
		uaxteGpsGnssAltitude OBJECT-TYPE
			SYNTAX Integer32
			UNITS "meter"
			MAX-ACCESS read-only
			STATUS current
			DESCRIPTION
				"meters above sealevel"
			::= { uaxteGpsGnss 5 }

		
		-- 1.3.6.1.4.1.43768.3.1.1.3.2.14.6
		uaxteGpsGnssHDOP OBJECT-TYPE
			SYNTAX Integer32
			UNITS "centi"
			MAX-ACCESS read-only
			STATUS current
			DESCRIPTION
				"Horzontal dilution of precesion.
				divide by 100, "
			::= { uaxteGpsGnss 6 }

		
		-- 1.3.6.1.4.1.43768.3.1.1.3.2.14.7
		uaxteGpsGnssAntennaPower OBJECT-TYPE
			SYNTAX INTEGER
				{
				fiveVolts(2),
				threePtThree(3)
				}
			MAX-ACCESS read-write
			STATUS current
			DESCRIPTION
				"5k or 3.3V"
			::= { uaxteGpsGnss 7 }

		
		-- 1.3.6.1.4.1.43768.3.1.1.3.2.14.8
		uaxteGpsGnssActive OBJECT-TYPE
			SYNTAX INTEGER
				{
				primary(1),
				secondary(2)
				}
			MAX-ACCESS read-write
			STATUS current
			DESCRIPTION
				"Current selection for Global Navigation Satellite System. Possible choices are Primary or Secondary."
			::= { uaxteGpsGnss 8 }

		
		-- 1.3.6.1.4.1.43768.3.1.1.3.2.14.9
		uaxteGpsGnssPrimary OBJECT-TYPE
			SYNTAX INTEGER
				{
				gps(1),
				glonass(2)
				}
			MAX-ACCESS read-write
			STATUS current
			DESCRIPTION
				"Primary Global Navigation Satellite System. Selection of U.S. GPS or the Russian GLONASS system is possible."
			::= { uaxteGpsGnss 9 }

		
		-- 1.3.6.1.4.1.43768.3.1.1.3.2.14.10
		uaxteGpsGnssSecondary OBJECT-TYPE
			SYNTAX INTEGER
				{
				gps(1),
				glonass(2)
				}
			MAX-ACCESS read-write
			STATUS current
			DESCRIPTION
				"Secondary Global Navigation Satellite System. Selection of U.S. GPS or the Russian GLONASS system is possible."
			::= { uaxteGpsGnss 10 }

		
		-- 1.3.6.1.4.1.43768.3.1.1.3.2.14.11
		uaxteGpsGnssSwitchMode OBJECT-TYPE
			SYNTAX INTEGER
				{
				manual(1),
				auto(2)
				}
			MAX-ACCESS read-write
			STATUS current
			DESCRIPTION
				"Switch mode for Global Navigation Satellite System selection. Possible choices are Auto or Manual."
			::= { uaxteGpsGnss 11 }

		
		-- 1.3.6.1.4.1.43768.3.1.1.3.2.14.12
		uaxteGpsGnssSwitchTimeout OBJECT-TYPE
			SYNTAX Integer32 (30..86400)
			UNITS "Seconds"
			MAX-ACCESS read-write
			STATUS current
			DESCRIPTION
				"Maximum time to search for the available GNSS before switching to another system (in seconds)."
			::= { uaxteGpsGnss 12 }

		
		-- 1.3.6.1.4.1.43768.3.1.1.3.2.14.13
		uaxteGpsGnssSwitchElapsedTime OBJECT-TYPE
			SYNTAX Integer32
			UNITS "Seconds"
			MAX-ACCESS read-only
			STATUS current
			DESCRIPTION
				"Time passed since current GNSS has became unavailable (in seconds). 
				When it reaches Switch Timeout the switching to another system occurs."
			::= { uaxteGpsGnss 13 }

		
		-- 1.3.6.1.4.1.43768.3.1.1.3.2.14.14
		uaxteGpsGnssSwitchMaxSwitchCount OBJECT-TYPE
			SYNTAX Integer32 (0..100000)
			MAX-ACCESS read-write
			STATUS current
			DESCRIPTION
				"This option limits number of times automatic switching may occur from one GNSS to another."
			::= { uaxteGpsGnss 14 }

		
		-- 1.3.6.1.4.1.43768.3.1.1.3.2.14.15
		uaxteGpsGnssSwitchCount OBJECT-TYPE
			SYNTAX Integer32
			MAX-ACCESS read-only
			STATUS current
			DESCRIPTION
				"Number of times automatic switching has been done between selected GNSS."
			::= { uaxteGpsGnss 15 }

		
		-- 1.3.6.1.4.1.43768.3.1.1.3.2.14.16
		uaxteGpsGnssSwitchCountReset OBJECT-TYPE
			SYNTAX Integer32 (1)
			MAX-ACCESS read-write
			STATUS current
			DESCRIPTION
				"Resets switch count & switch elapsed time counters"
			::= { uaxteGpsGnss 16 }

		
		-- 1.3.6.1.4.1.43768.3.1.1.3.2.15
		uaxteSnmp OBJECT IDENTIFIER ::= { uaxteObjects 15 }

		
		-- 1.3.6.1.4.1.43768.3.1.1.3.2.15.1
		uaxteSnmpPortNumber OBJECT-TYPE
			SYNTAX Integer32
			MAX-ACCESS read-write
			STATUS current
			DESCRIPTION
				"The UDP port number on which the SNMP agent
				should listen for GET and SET PDUs."
			::= { uaxteSnmp 1 }

		
		-- 1.3.6.1.4.1.43768.3.1.1.3.2.15.2
		uaxteSnmpTrapVersion OBJECT-TYPE
			SYNTAX Integer32
			MAX-ACCESS read-write
			STATUS current
			DESCRIPTION
				"The trap format, v1 or v2c, that the SNMP agent
				should use for reporting events"
			::= { uaxteSnmp 2 }

		
		-- 1.3.6.1.4.1.43768.3.1.1.3.2.15.3
		uaxteSnmpTrapHostTable OBJECT-TYPE
			SYNTAX SEQUENCE OF UaxteSnmpTrapHostEntry
			MAX-ACCESS not-accessible
			STATUS current
			DESCRIPTION
				"Description."
			::= { uaxteSnmp 3 }

		
		-- 1.3.6.1.4.1.43768.3.1.1.3.2.15.3.1
		uaxteSnmpTrapHostEntry OBJECT-TYPE
			SYNTAX UaxteSnmpTrapHostEntry
			MAX-ACCESS not-accessible
			STATUS current
			DESCRIPTION
				"Description."
			INDEX { uaxteSnmpTrapHostIndex }
			::= { uaxteSnmpTrapHostTable 1 }

		
		UaxteSnmpTrapHostEntry ::=
			SEQUENCE { 
				uaxteSnmpTrapHostIndex
					Integer32,
				uaxteSnmpTrapHostIpAddress
					IpAddress,
				uaxteSnmpTrapHostPort
					Integer32,
				uaxteSnmpTrapHostPduType
					SNMPEventType,
				uaxteSnmpTrapHostInformRetries
					Integer32,
				uaxteSnmpTrapHostInformRetryInterval
					Integer32,
				uaxteSnmpTrapHostOutstandingInforms
					Integer32
			 }

		-- 1.3.6.1.4.1.43768.3.1.1.3.2.15.3.1.1
		uaxteSnmpTrapHostIndex OBJECT-TYPE
			SYNTAX Integer32 (1..3)
			MAX-ACCESS read-only
			STATUS current
			DESCRIPTION
				"The index used to access this trap receiver."
			::= { uaxteSnmpTrapHostEntry 1 }

		
		-- 1.3.6.1.4.1.43768.3.1.1.3.2.15.3.1.2
		uaxteSnmpTrapHostIpAddress OBJECT-TYPE
			SYNTAX IpAddress
			MAX-ACCESS read-write
			STATUS current
			DESCRIPTION
				"The IP address of the trap receiver."
			::= { uaxteSnmpTrapHostEntry 2 }

		
		-- 1.3.6.1.4.1.43768.3.1.1.3.2.15.3.1.3
		uaxteSnmpTrapHostPort OBJECT-TYPE
			SYNTAX Integer32
			MAX-ACCESS read-write
			STATUS current
			DESCRIPTION
				"The UDP port number that the agent should use
				to send a trap to this trap receiver."
			::= { uaxteSnmpTrapHostEntry 3 }

		
		-- 1.3.6.1.4.1.43768.3.1.1.3.2.15.3.1.4
		uaxteSnmpTrapHostPduType OBJECT-TYPE
			SYNTAX SNMPEventType
			MAX-ACCESS read-write
			STATUS current
			DESCRIPTION
				"Configures whether the agent should report events
				to this trap receiver in TRAP or INFORM PDUs."
			::= { uaxteSnmpTrapHostEntry 4 }

		
		-- 1.3.6.1.4.1.43768.3.1.1.3.2.15.3.1.5
		uaxteSnmpTrapHostInformRetries OBJECT-TYPE
			SYNTAX Integer32
			MAX-ACCESS read-write
			STATUS current
			DESCRIPTION
				"Defines the number of times the agent should send
				an INFORM PDU to the trap receiver without receiving
				an acknowledgement."
			::= { uaxteSnmpTrapHostEntry 5 }

		
		-- 1.3.6.1.4.1.43768.3.1.1.3.2.15.3.1.6
		uaxteSnmpTrapHostInformRetryInterval OBJECT-TYPE
			SYNTAX Integer32
			MAX-ACCESS read-write
			STATUS current
			DESCRIPTION
				"The time interval, in seconds, between attempts
				to send the INFORM PDU to the trap receiver."
			::= { uaxteSnmpTrapHostEntry 6 }

		
		-- 1.3.6.1.4.1.43768.3.1.1.3.2.15.3.1.7
		uaxteSnmpTrapHostOutstandingInforms OBJECT-TYPE
			SYNTAX Integer32
			MAX-ACCESS read-write
			STATUS current
			DESCRIPTION
				"The maximum number of unacknowledged INFORM PDUs
				allowed before the agent stops trying to resend
				an INFORM PDU. For example, if this element is set
				to 5, there are 5 INFORM PDU's for which the agent
				is awaiting an acknowledgement, and a sixth INFORM
				needs to be sent, the agent will stop resending and
				waiting for an acknowledgement on the oldest outstanding
				PDU."
			::= { uaxteSnmpTrapHostEntry 7 }

		
		-- 1.3.6.1.4.1.43768.3.1.1.3.2.16
		uaxteEventEnables OBJECT IDENTIFIER ::= { uaxteObjects 16 }

		
		-- 1.3.6.1.4.1.43768.3.1.1.3.2.16.1
		uaxteEventEnableGeneral OBJECT IDENTIFIER ::= { uaxteEventEnables 1 }

		
		-- 1.3.6.1.4.1.43768.3.1.1.3.2.16.1.1
		uaxteAllEventsEnable OBJECT-TYPE
			SYNTAX EnabledDisabled
			MAX-ACCESS read-write
			STATUS current
			DESCRIPTION
				"Enable/Disable all events, 0= Enable/Disble event individually, 1=Enable all events, 2=Disable all events."
			::= { uaxteEventEnableGeneral 1 }

		
		-- 1.3.6.1.4.1.43768.3.1.1.3.2.16.1.2
		uaxteOpModeEventEnable OBJECT-TYPE
			SYNTAX EnabledDisabled
			MAX-ACCESS read-write
			STATUS current
			DESCRIPTION
				"Enable/Disable uaxteOpModeEvent = Enable event, 2 = Disable event"
			::= { uaxteEventEnableGeneral 2 }

		
		-- 1.3.6.1.4.1.43768.3.1.1.3.2.16.1.3
		uaxteActiveEventEnable OBJECT-TYPE
			SYNTAX EnabledDisabled
			MAX-ACCESS read-write
			STATUS current
			DESCRIPTION
				"Enable/Disable uaxteActiveEvent = Enable event, 2 = Disable event"
			::= { uaxteEventEnableGeneral 3 }

		
		-- 1.3.6.1.4.1.43768.3.1.1.3.2.16.1.4
		uaxteStatusEventEnable OBJECT-TYPE
			SYNTAX EnabledDisabled
			MAX-ACCESS read-write
			STATUS current
			DESCRIPTION
				"Enable/Disable uaxteStatusEvent = Enable event, 2 = Disable event"
			::= { uaxteEventEnableGeneral 4 }

		
		-- 1.3.6.1.4.1.43768.3.1.1.3.2.16.1.5
		uaxteInputStatusPrimaryEventEnable OBJECT-TYPE
			SYNTAX EnabledDisabled
			MAX-ACCESS read-write
			STATUS current
			DESCRIPTION
				"Enable/Disable uaxteInputPrimaryEvent = Enable event, 2 = Disable event"
			::= { uaxteEventEnableGeneral 5 }

		
		-- 1.3.6.1.4.1.43768.3.1.1.3.2.16.1.6
		uaxteInputStatusSecondaryEventEnable OBJECT-TYPE
			SYNTAX EnabledDisabled
			MAX-ACCESS read-write
			STATUS current
			DESCRIPTION
				"Enable/Disable uaxteInputSecondaryEvent = Enable event, 2 = Disable event"
			::= { uaxteEventEnableGeneral 6 }

		
		-- 1.3.6.1.4.1.43768.3.1.1.3.2.16.1.7
		uaxteInputSwitchCountCurrentEnable OBJECT-TYPE
			SYNTAX EnabledDisabled
			MAX-ACCESS read-write
			STATUS current
			DESCRIPTION
				"Enable/Disable uaxteInputSwitchCountCurrentEvent = Enable event, 2 = Disable event"
			::= { uaxteEventEnableGeneral 7 }

		
		-- 1.3.6.1.4.1.43768.3.1.1.3.2.16.1.8
		uaxteOutputForwardLowWarningEventEnable OBJECT-TYPE
			SYNTAX EnabledDisabled
			MAX-ACCESS read-write
			STATUS current
			DESCRIPTION
				"Enable/Disable uaxteOutputForwardLowWarningEvent = Enable event, 2 = Disable event"
			::= { uaxteEventEnableGeneral 8 }

		
		-- 1.3.6.1.4.1.43768.3.1.1.3.2.16.1.9
		uaxteOutputForwardLowFaultEventEnable OBJECT-TYPE
			SYNTAX EnabledDisabled
			MAX-ACCESS read-write
			STATUS current
			DESCRIPTION
				"Enable/Disable uaxteOutputForwardLowFaultEvent = Enable event, 2 = Disable event"
			::= { uaxteEventEnableGeneral 9 }

		
		-- 1.3.6.1.4.1.43768.3.1.1.3.2.16.1.10
		uaxteOutputForwardHighFaultEventEnable OBJECT-TYPE
			SYNTAX EnabledDisabled
			MAX-ACCESS read-write
			STATUS current
			DESCRIPTION
				"Enable/Disable uaxteOutputForwardHighFaultWarningEvent = Enable event, 2 = Disable event"
			::= { uaxteEventEnableGeneral 10 }

		
		-- 1.3.6.1.4.1.43768.3.1.1.3.2.16.1.11
		uaxteOutputMuteEventEnable OBJECT-TYPE
			SYNTAX EnabledDisabled
			MAX-ACCESS read-write
			STATUS current
			DESCRIPTION
				"Enable/Disable uaxteOutputMuteEvent = Enable event, 2 = Disable event"
			::= { uaxteEventEnableGeneral 11 }

		
		-- 1.3.6.1.4.1.43768.3.1.1.3.2.16.1.12
		uaxteRtacLinearModeEventEnable OBJECT-TYPE
			SYNTAX EnabledDisabled
			MAX-ACCESS read-write
			STATUS current
			DESCRIPTION
				"Enable/Disable uaxteRtacLinearModeEvent = Enable event, 2 = Disable event"
			::= { uaxteEventEnableGeneral 12 }

		
		-- 1.3.6.1.4.1.43768.3.1.1.3.2.16.1.13
		uaxteRtacNonLinearModeEventEnable OBJECT-TYPE
			SYNTAX EnabledDisabled
			MAX-ACCESS read-write
			STATUS current
			DESCRIPTION
				"Enable/Disable uaxteRtacNonLinearModeEvent = Enable event, 2 = Disable event"
			::= { uaxteEventEnableGeneral 13 }

		
		-- 1.3.6.1.4.1.43768.3.1.1.3.2.16.1.14
		uaxteRtacDisabledEventEnable OBJECT-TYPE
			SYNTAX EnabledDisabled
			MAX-ACCESS read-write
			STATUS current
			DESCRIPTION
				"Enable/Disable uaxteRtacDisableEvent = Enable event, 2 = Disable event"
			::= { uaxteEventEnableGeneral 14 }

		
		-- 1.3.6.1.4.1.43768.3.1.1.3.2.16.1.15
		uaxtePwrSupplyControllerEventEnable OBJECT-TYPE
			SYNTAX EnabledDisabled
			MAX-ACCESS read-write
			STATUS current
			DESCRIPTION
				"Enable/Disable uaxtePwrSupplyControllerEvent = Enable event, 2 = Disable event"
			::= { uaxteEventEnableGeneral 15 }

		
		-- 1.3.6.1.4.1.43768.3.1.1.3.2.16.1.16
		uaxtePwrSupplyPwrAmpEventEnable OBJECT-TYPE
			SYNTAX EnabledDisabled
			MAX-ACCESS read-write
			STATUS current
			DESCRIPTION
				"Enable/Disable uaxtePwrSupplyPwrAmpEvent = Enable event, 2 = Disable event"
			::= { uaxteEventEnableGeneral 16 }

		
		-- 1.3.6.1.4.1.43768.3.1.1.3.2.16.1.17
		uaxtePwrSupplyModulatorEventEnable OBJECT-TYPE
			SYNTAX EnabledDisabled
			MAX-ACCESS read-write
			STATUS current
			DESCRIPTION
				"Enable/Disable uaxtePwrSupplyModulatorEvent = Enable event, 2 = Disable event"
			::= { uaxteEventEnableGeneral 17 }

		
		-- 1.3.6.1.4.1.43768.3.1.1.3.2.16.1.18
		uaxteRtacPerfValidEventEnable OBJECT-TYPE
			SYNTAX EnabledDisabled
			MAX-ACCESS read-write
			STATUS current
			DESCRIPTION
				"Enable/Disable uaxteRtacPerfValidEvent = Enable event, 2 = Disable event"
			::= { uaxteEventEnableGeneral 18 }

		
		-- 1.3.6.1.4.1.43768.3.1.1.3.2.16.2
		uaxteEventEnablePwrAmps OBJECT IDENTIFIER ::= { uaxteEventEnables 2 }

		
		-- 1.3.6.1.4.1.43768.3.1.1.3.3
		uaxteConformance OBJECT IDENTIFIER ::= { uaxteBaseMib 3 }

		
		-- 1.3.6.1.4.1.43768.3.1.1.3.3.1
		uaxteObjectGroups OBJECT-GROUP
			OBJECTS { uaxteMibRevision, uaxteVerSwPartNumber, uaxteVerSwRev, uaxteVerSwUboot, uaxteVerSwWebboot, 
				uaxteVerSwXtmod, uaxteVerSwLinux, uaxteVerSwDevTree, uaxteVerSwFpga1, uaxteVerSwFpga2, 
				uaxteVerSwCpld, uaxteVerHwModulator, uaxteVerHwBackplane, uaxteVerHwPwrSupplyCtrl, uaxteVerHwPwrAmp, 
				uaxteOpMode, uaxteActive, uaxteStatus, uaxteStationName, uaxteModelNumber, 
				uaxteSerialNumber, uaxteTimeOfDay, uaxteUTCOffset, uaxteTimeSource, uaxteNTPServerName1, 
				uaxteNTPServerName2, uaxteNTPServerName3, uaxteNTPServerName4, uaxteNTPServerName5, uaxteInputPowerOn, 
				uaxteInputActive, uaxteInputStatusPrimary, uaxteInputStatusSecondary, uaxteInputMuteOnTsLoss, uaxteInputSwitchMode, 
				uaxteInputSwitchTimeout, uaxteInputSwitchElapsedTime, uaxteInputSwitchCountMax, uaxteInputSwitchCountCurrent, uaxteInputSwitchCountReset, 
				uaxtePaSystemFaultAcMains, uaxtePaSystemFaultRs485Communication, uaxtePaSystemSummary, uaxtePaSystemNumberOfCabinets, uaxtePaSystemNumberOfIPAsPerCabinet, 
				uaxtePaSystemNumberOfPAsPerCabinet, uaxtePaSystemNumberOfPalletsPerPAs, uaxteCabIndex, uaxteCabFaultAcMain, uaxteCabFaultPaRs485Communication, 
				uaxteCabFaultRs485Communication, uaxteCabFaultSummary, uaxtePaCabIndex, uaxtePaIndex, uaxtePaOpMode, 
				uaxtePaFwdPwr, uaxtePaRfldPwr, uaxtePaVolts, uaxtePaTemperature, uaxtePaPreAmpCurent, 
				uaxtePaPallet1Current, uaxtePaPallet2Current, uaxtePaPallet3Current, uaxtePaPallet4Current, uaxtePaPallet5Current, 
				uaxtePaPallet6Current, uaxtePaPallet7Current, uaxtePaPallet8Current, uaxtePaFaultAcMain, uaxtePaFaultsRs485Communication, 
				uaxteIpaCabIndex, uaxteIpaIndex, uaxteIpaOpMode, uaxteIpaFwdPwr, uaxteIpaRfldPwr, 
				uaxteIpaVolts, uaxteIpaTemperature, uaxteIpaPreAmpCurrent, uaxteIpaPallet1Current, uaxteIpaPallet2Current, 
				uaxteIpaPallet3Current, uaxteIpaPallet4Current, uaxteIpaPallet5Current, uaxteIpaPallet6Current, uaxteIpaPallet7Current, 
				uaxteIpaPallet8Current, uaxteIpaFaultAcMain, uaxteIpaFaultsRs485Communication, uaxteDriverFwdPwr, uaxteDriverRfldPwr, 
				uaxteDriverInputRms, uaxteDriverCurrent, uaxteDriverTemperature, uaxteDriverVoltage, uaxteOutputLpuForward, 
				uaxteOutputLpuReflected, uaxteOutputSystemForward, uaxteOutputSystemReflected, uaxteOutputForwardLowWarning, uaxteOutputForwardLowFault, 
				uaxteOutputForwardHighFault, uaxteOutputMute, uaxteCfgForwardAPCReference, uaxteCfgForwardNominal, uaxteCfgForwardLowWarning, 
				uaxteCfgForwardLowFault, uaxteCfgForwardHighFault, uaxteCfgRfldFoldbackThreshold, uaxteCfgPwrCntrlMode, uaxteCfgPwrCntrlDriveLevel, 
				uaxteCfgPwrCntrlDriveLevelAdjust, uaxteCfgPwrCntrlDriveLimit, uaxteCfgPwrCntrlInputAttenuatorLevel, uaxteCfgPwrCntrlInputAttenuatorLevelAdjust, uaxteCfgAcRestartDelay, 
				uaxteRtacDisabled, uaxteRtacSetupPeakReductionMode, uaxteRtacSetupNonLinearRange, uaxteRtacSetupMaxCrestFactor, uaxteRtacLinearMode, 
				uaxteRtacLinearSuccess, uaxteRtacLinearAttempts, uaxteRtacLinearModeAfterAcLoss, uaxteRtacNonLinearMode, uaxteRtacNonLinearSuccess, 
				uaxteRtacNonLinearAttempts, uaxteRtacNonLinearModeAfterAcLoss, uaxteRtacPerfLSB, uaxteRtacPerfUSB, uaxteRtacPerfEVM, 
				uaxteRtacPerfMERSNR, uaxteRtacPerfValid, uaxtePwrSupplyController, uaxtePwrSupplyPwrAmp, uaxtePwrSupplyModulator, 
				uaxteCoolingTempAmbient, uaxteCoolingTempPwrAmp, uaxteCoolingTempFpga1, uaxteCoolingTempFpga2, uaxteKernelTemp, 
				uaxteCoolingTempBattery, uaxteCoolingRpmFan1, uaxteCoolingRpmFan2, uaxteCoolingRpmFan3, uaxteCoolingRpmFan4, 
				uaxteNetworkIndex, uaxteNetworkMac, uaxteNetworkAddr, uaxteNetworkNetmask, uaxteNetworkLink, 
				uaxteNetworkDuplexMode, uaxteNetworkSpeed, uaxteNetworkAutoNegotiate, uaxteInputNetworkIndex, uaxteInputNetworkMode, 
				uaxteInputNetworkDestAddress, uaxteInputNetworkDestPort, uaxteInputNetworkSourceFilter, uaxteInputNetworkSourceAddress, uaxteInputNetworkSourcePort, 
				uaxteInputNetworkSMPTE2022Mode, uaxteInputNetworkRxBytes, uaxteInputNetworkRxFrames, uaxteInputNetworkTxBytes, uaxteInputNetworkTxFrames, 
				uaxteInputNetworkIGMPRequest, uaxteInputNetworkIGMPReports, uaxteInputNetworkUDPReceived, uaxteInputNetworkUDPDiscarded, uaxteInputNetworkUDPErrors, 
				uaxteInputNetworkResetStats, uaxteInputNetworkFecRecoved, uaxteInputNetworkFecLost, uaxteInputNetworkFecLValue, uaxteInputNetworkFecDValue, 
				uaxteInputNetworkFecResetStats, uaxteOcxoReferenceSystem, uaxteOcxoTuning, uaxteOcxoRfOutIfUndisciplined, uaxteOcxo1ppsInputPrimary, 
				uaxteOcxo1ppsInputActual, uaxteOcxoGnssMode, uaxteOcxoReferenceInput, uaxteOcxoReferenceInputTermination, uaxteOcxoReferenceOutput, 
				uaxteOcxoReferenceLossMute, uaxteOcxoReferenceTimeout, uaxteFtrReadiness, uaxteFtrTimeRemaining, uaxteFtrSystemRefInput, 
				uaxteFtrSystemRefIntGps1pps, uaxteFtrPllRefClock, uaxteFtrPllLockRfLo1, uaxteFtrPllLockRfLo2, uaxteFtrPllLockDigital, 
				uaxteFtrFrequency, uaxteGpsGnssNumberofSatellites, uaxteGpsGnssSatelliteTime, uaxteGpsGnssLatitude, uaxteGpsGnssLongitude, 
				uaxteGpsGnssAltitude, uaxteGpsGnssHDOP, uaxteGpsGnssAntennaPower, uaxteGpsGnssActive, uaxteGpsGnssPrimary, 
				uaxteGpsGnssSecondary, uaxteGpsGnssSwitchMode, uaxteGpsGnssSwitchTimeout, uaxteGpsGnssSwitchElapsedTime, uaxteGpsGnssSwitchMaxSwitchCount, 
				uaxteGpsGnssSwitchCount, uaxteGpsGnssSwitchCountReset, uaxteSnmpPortNumber, uaxteSnmpTrapVersion, uaxteSnmpTrapHostIndex, 
				uaxteSnmpTrapHostIpAddress, uaxteSnmpTrapHostPort, uaxteSnmpTrapHostPduType, uaxteSnmpTrapHostInformRetries, uaxteSnmpTrapHostInformRetryInterval, 
				uaxteSnmpTrapHostOutstandingInforms, uaxteAllEventsEnable, uaxteOpModeEventEnable, uaxteActiveEventEnable, uaxteStatusEventEnable, 
				uaxteInputStatusPrimaryEventEnable, uaxteInputStatusSecondaryEventEnable, uaxteInputSwitchCountCurrentEnable, uaxteOutputForwardLowWarningEventEnable, uaxteOutputForwardLowFaultEventEnable, 
				uaxteOutputForwardHighFaultEventEnable, uaxteOutputMuteEventEnable, uaxteRtacLinearModeEventEnable, uaxteRtacNonLinearModeEventEnable, uaxteRtacDisabledEventEnable, 
				uaxtePwrSupplyControllerEventEnable, uaxtePwrSupplyPwrAmpEventEnable, uaxtePwrSupplyModulatorEventEnable, uaxteRtacPerfValidEventEnable }
			STATUS current
			DESCRIPTION 
				"Description."
			::= { uaxteConformance 1 }

		
		-- 1.3.6.1.4.1.43768.3.1.1.3.3.2
		uaxteEventsGroups NOTIFICATION-GROUP
			NOTIFICATIONS { uaxteOpModeEvent, uaxteStatusEvent, uaxteInputStatusPrimaryEvent, uaxteInputStatusSecondaryEvent, uaxteInputSwitchCountCurrentEvent, 
				uaxteOutputForwardLowWarningEvent, uaxteOutputForwardLowFaultEvent, uaxteOutputForwardHighFaultEvent, uaxteOutputMuteEvent, uaxteRtacLinearModeEvent, 
				uaxteRtacNonLinearModeEvent, uaxteRtacDisabledEvent, uaxtePwrSupplyControllerEvent, uaxtePwrSupplyPwrAmpEvent, uaxtePwrSupplyModulatorEvent, 
				uaxteRtacPerfValidEvent, uaxteActiveEvent }
			STATUS current
			DESCRIPTION 
				"Description."
			::= { uaxteConformance 2 }

		
		-- 1.3.6.1.4.1.43768.3.1.1.3.3.3
		uaxteCompliances MODULE-COMPLIANCE
			STATUS current
			DESCRIPTION 
				"Description."
			MODULE -- this module
				MANDATORY-GROUPS { uaxteObjectGroups, uaxteEventsGroups }
			::= { uaxteConformance 3 }

		
		-- 1.3.6.1.4.1.43768.3.1.1.3.3.4
		uaxteObjectsGroupsObsolote OBJECT-GROUP
			OBJECTS { uaxteCfgRfldFault }
			STATUS obsolete
			DESCRIPTION 
				"objects in this group are no longer used they are obsolete"
			::= { uaxteConformance 4 }

		
	
	END

--
-- GATESAIR-UAXTE-MIB.my
--
